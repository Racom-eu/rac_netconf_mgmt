module "mbm-root" {
    yang-version "1.1";
    namespace "eu:racom:mbm:root";
    prefix "rr";
    import "ietf-yang-types" {
        prefix "yang";
        revision-date "2025-12-22";
    }
    import "ietf-inet-types" {
        prefix "inet";
        revision-date "2025-12-22";
    }
    organization "
	Racom s.r.o.
	Mirova 1283
	Nove Mesto na Morave
	59231
	Czech Republic
	www.racom.eu";
    description "Root module of product yang schema";
    revision "2023-04-29" {
        description "Company name part removed from module names.";
    }
    revision "2023-04-15" {
        description "Model generation restructured.";
    }
    revision "2022-08-07" {
        description "Yang model initial revision.
		Note: Configuration version changes are currently
		NOT followed by model revision update.";
    }
    container "config_data" {
        typedef "lbox_off_on" {
            type "enumeration" {
                enum "Off" {
                    value "0";
                }
                enum "On" {
                    value "1";
                }
            }
        }
        typedef "lbox_eth_autoneg_M1" {
            type "enumeration" {
                enum "LB_eth_autoneg_auto_auto" {
                    value "0";
                }
                enum "LB_eth_autoneg_auto_full" {
                    value "1";
                }
                enum "LB_eth_autoneg_auto_half" {
                    value "2";
                }
                enum "LB_eth_autoneg_1000mbps_auto" {
                    value "3";
                }
                enum "LB_eth_autoneg_1000mbps_full" {
                    value "4";
                }
                enum "LB_eth_autoneg_1000mbps_half" {
                    value "5";
                }
                enum "LB_eth_autoneg_100mbps_auto" {
                    value "6";
                }
                enum "LB_eth_autoneg_100mbps_full" {
                    value "7";
                }
                enum "LB_eth_autoneg_100mbps_half" {
                    value "8";
                }
                enum "LB_eth_autoneg_10mbps_auto" {
                    value "9";
                }
                enum "LB_eth_autoneg_10mbps_full" {
                    value "10";
                }
                enum "LB_eth_autoneg_10mbps_half" {
                    value "11";
                }
            }
        }
        typedef "lbox_event_severity" {
            type "enumeration" {
                enum "Emergency" {
                    value "0";
                }
                enum "Alert" {
                    value "1";
                }
                enum "Critical" {
                    value "2";
                }
                enum "Error" {
                    value "3";
                }
                enum "Warning" {
                    value "4";
                }
                enum "Notice" {
                    value "5";
                }
                enum "Informational" {
                    value "6";
                }
                enum "Debug" {
                    value "7";
                }
            }
        }
        typedef "lbox_event_severity_warn_up" {
            type "enumeration" {
                enum "Emergency" {
                    value "0";
                }
                enum "Alert" {
                    value "1";
                }
                enum "Critical" {
                    value "2";
                }
                enum "Error" {
                    value "3";
                }
                enum "Warning" {
                    value "4";
                }
                enum "Notice" {
                    value "5";
                }
                enum "Informational" {
                    value "6";
                }
                enum "Debug" {
                    value "7";
                }
            }
        }
        typedef "lbox_radio_modulation_M7" {
            type "enumeration" {
                enum "2CPFSK" {
                    value "0";
                }
                enum "4CPFSK" {
                    value "1";
                }
                enum "DPSK" {
                    value "8";
                }
                enum "pi/4DQPSK" {
                    value "9";
                }
                enum "D8PSK" {
                    value "10";
                }
                enum "16DEQAM" {
                    value "11";
                }
                enum "64QAM" {
                    value "12";
                }
                enum "256QAM" {
                    value "13";
                }
            }
        }
        typedef "lbox_radio_fec_M9" {
            type "enumeration" {
                enum "1/1" {
                    value "0";
                }
                enum "5/6" {
                    value "1";
                }
                enum "3/4" {
                    value "2";
                }
                enum "2/3" {
                    value "3";
                }
            }
        }
        typedef "lbox_radio_acm_profiles_M1" {
            type "enumeration" {
                enum "LB_radio_acm_profiles_2CPFSK_3_4" {
                    value "0";
                }
                enum "LB_radio_acm_profiles_4CPFSK_3_4" {
                    value "1";
                }
                enum "LB_radio_acm_profiles_4CPFSK_1_1" {
                    value "2";
                }
                enum "LB_radio_acm_profiles_DPSK_3_4" {
                    value "8";
                }
                enum "LB_radio_acm_profiles_pi4DQPSK_3_4" {
                    value "9";
                }
                enum "LB_radio_acm_profiles_16DEQAM_3_4" {
                    value "10";
                }
                enum "LB_radio_acm_profiles_64QAM_3_4" {
                    value "11";
                }
                enum "LB_radio_acm_profiles_256QAM_3_4" {
                    value "12";
                }
                enum "LB_radio_acm_profiles_256QAM_5_6" {
                    value "13";
                }
            }
        }
        typedef "lbox_psk_key_mode" {
            type "enumeration" {
                enum "Pass Phrase" {
                    value "0";
                }
                enum "Key" {
                    value "1";
                }
            }
        }
        typedef "lbox_wifi_mac_acl" {
            type "enumeration" {
                enum "LB_wifi_mac_acl_Off" {
                    value "0";
                }
                enum "LB_wifi_mac_acl_Accept" {
                    value "1";
                }
                enum "LB_wifi_mac_acl_Deny" {
                    value "2";
                }
            }
        }
        typedef "lbox_wifi_security" {
            type "enumeration" {
                enum "LB_wifi_security_Off" {
                    value "0";
                }
                enum "LB_wifi_security_Wpa" {
                    value "1";
                }
                enum "LB_wifi_security_Wpa2" {
                    value "2";
                }
                enum "LB_wifi_security_WpaWpa2" {
                    value "3";
                }
                enum "LB_wifi_security_Wpa3" {
                    value "4";
                }
                enum "LB_wifi_security_Wpa2Wpa3" {
                    value "5";
                }
            }
        }
        typedef "lbox_antenna_config" {
            type "enumeration" {
                enum "LB_antenna_config_Off" {
                    value "0";
                }
                enum "LB_antenna_config_Tx" {
                    value "1";
                }
                enum "LB_antenna_config_Rx" {
                    value "2";
                }
                enum "LB_antenna_config_TxRx" {
                    value "3";
                }
            }
        }
        typedef "lbox_fwall_filter_limit_period" {
            type "enumeration" {
                enum "LB_fwall_filter_limit_period_V_second" {
                    value "0";
                }
                enum "LB_fwall_filter_limit_period_V_minute" {
                    value "1";
                }
                enum "LB_fwall_filter_limit_period_V_hour" {
                    value "2";
                }
                enum "LB_fwall_filter_limit_period_V_day" {
                    value "3";
                }
            }
        }
        typedef "lbox_adr_filter_policy" {
            type "enumeration" {
                enum "Accept" {
                    value "0";
                }
                enum "Reject" {
                    value "1";
                }
            }
        }
        typedef "lbox_default_user" {
            type "enumeration" {
                enum "LB_default_user_Default" {
                    value "0";
                }
                enum "LB_default_user_User" {
                    value "1";
                }
            }
        }
        typedef "lbox_event_severity_error_down" {
            type "enumeration" {
                enum "Emergency" {
                    value "0";
                }
                enum "Alert" {
                    value "1";
                }
                enum "Critical" {
                    value "2";
                }
                enum "Error" {
                    value "3";
                }
                enum "Warning" {
                    value "4";
                }
                enum "Notice" {
                    value "5";
                }
                enum "Informational" {
                    value "6";
                }
                enum "Debug" {
                    value "7";
                }
            }
        }
        typedef "lbox_event_severity_info_down" {
            type "enumeration" {
                enum "Emergency" {
                    value "0";
                }
                enum "Alert" {
                    value "1";
                }
                enum "Critical" {
                    value "2";
                }
                enum "Error" {
                    value "3";
                }
                enum "Warning" {
                    value "4";
                }
                enum "Notice" {
                    value "5";
                }
                enum "Informational" {
                    value "6";
                }
                enum "Debug" {
                    value "7";
                }
            }
        }
        typedef "lbox_transport_protocol" {
            type "enumeration" {
                enum "LB_transport_protocol_Udp" {
                    value "0";
                }
                enum "LB_transport_protocol_Tcp" {
                    value "1";
                }
            }
        }
        typedef "lbox_hw_io" {
            type "enumeration" {
                enum "NO" {
                    value "0";
                }
                enum "NC" {
                    value "1";
                }
            }
        }
        typedef "lbox_com_port_1_type_M3" {
            type "enumeration" {
                enum "RS232" {
                    value "0";
                }
                enum "RS485" {
                    value "1";
                }
            }
        }
        typedef "lbox_com_port_baud_rate" {
            type "enumeration" {
                enum "300 B" {
                    value "0";
                }
                enum "600 B" {
                    value "1";
                }
                enum "1200 B" {
                    value "2";
                }
                enum "2400 B" {
                    value "3";
                }
                enum "4800 B" {
                    value "4";
                }
                enum "9600 B" {
                    value "5";
                }
                enum "19200 B" {
                    value "6";
                }
                enum "38400 B" {
                    value "7";
                }
                enum "57600 B" {
                    value "8";
                }
                enum "115200 B" {
                    value "9";
                }
                enum "230400 B" {
                    value "10";
                }
                enum "460800 B" {
                    value "11";
                }
                enum "500000 B" {
                    value "12";
                }
                enum "576000 B" {
                    value "13";
                }
                enum "921600 B" {
                    value "14";
                }
                enum "1000000 B" {
                    value "15";
                }
                enum "1152000 B" {
                    value "16";
                }
            }
        }
        typedef "lbox_com_port_1_data_bits_M2" {
            type "enumeration" {
                enum "5 bits" {
                    value "2";
                }
                enum "6 bits" {
                    value "3";
                }
                enum "7 bits" {
                    value "0";
                }
                enum "8 bits" {
                    value "1";
                }
            }
        }
        typedef "lbox_com_port_1_parity_M2" {
            type "enumeration" {
                enum "NONE" {
                    value "0";
                }
                enum "ODD" {
                    value "1";
                }
                enum "EVEN" {
                    value "2";
                }
            }
        }
        typedef "lbox_com_port_1_stop_bits_M1" {
            type "enumeration" {
                enum "1 bit" {
                    value "0";
                }
                enum "2 bits" {
                    value "1";
                }
            }
        }
        typedef "lbox_com_port_1_flow_ctrl_M3" {
            type "enumeration" {
                enum "NONE" {
                    value "0";
                }
                enum "RTS/CTS" {
                    value "1";
                }
            }
        }
        typedef "lbox_protocols_COM_M9" {
            type "enumeration" {
                enum "None" {
                    value "0";
                }
                enum "Transparent" {
                    value "4";
                }
                enum "Async_Link" {
                    value "1";
                }
                enum "COMLI" {
                    value "14";
                }
                enum "DNP3" {
                    value "2";
                }
                enum "DF1" {
                    value "3";
                }
                enum "IEC101" {
                    value "5";
                }
                enum "Mars-A" {
                    value "13";
                }
                enum "ModbusRTU" {
                    value "8";
                }
                enum "PPP" {
                    value "15";
                }
                enum "PR2000" {
                    value "10";
                }
                enum "RDS" {
                    value "7";
                }
                enum "S3964R" {
                    value "11";
                }
                enum "SAIA_S-BUS" {
                    value "12";
                }
                enum "UNI" {
                    value "6";
                }
            }
        }
        typedef "lbox_com_port_2_baud_rate" {
            type "enumeration" {
                enum "300 B" {
                    value "0";
                }
                enum "600 B" {
                    value "1";
                }
                enum "1200 B" {
                    value "2";
                }
                enum "2400 B" {
                    value "3";
                }
                enum "4800 B" {
                    value "4";
                }
                enum "9600 B" {
                    value "5";
                }
                enum "19200 B" {
                    value "6";
                }
                enum "38400 B" {
                    value "7";
                }
                enum "57600 B" {
                    value "8";
                }
                enum "115200 B" {
                    value "9";
                }
                enum "230400 B" {
                    value "10";
                }
                enum "460800 B" {
                    value "11";
                }
                enum "500000 B" {
                    value "12";
                }
                enum "576000 B" {
                    value "13";
                }
                enum "921600 B" {
                    value "14";
                }
                enum "1000000 B" {
                    value "15";
                }
                enum "1152000 B" {
                    value "16";
                }
                enum "1500000 B" {
                    value "17";
                }
                enum "2000000 B" {
                    value "18";
                }
            }
        }
        typedef "lbox_com_port_2_data_bits_M2" {
            type "enumeration" {
                enum "5 bits" {
                    value "2";
                }
                enum "6 bits" {
                    value "3";
                }
                enum "7 bits" {
                    value "0";
                }
                enum "8 bits" {
                    value "1";
                }
            }
        }
        typedef "lbox_com_port_2_parity_M2" {
            type "enumeration" {
                enum "NONE" {
                    value "0";
                }
                enum "ODD" {
                    value "1";
                }
                enum "EVEN" {
                    value "2";
                }
            }
        }
        typedef "lbox_com_port_2_stop_bits_M1" {
            type "enumeration" {
                enum "1 bit" {
                    value "0";
                }
                enum "2 bits" {
                    value "1";
                }
            }
        }
        typedef "lbox_com_port_2_flow_ctrl_M1" {
            type "enumeration" {
                enum "NONE" {
                    value "0";
                }
                enum "RTS/CTS" {
                    value "1";
                }
            }
        }
        typedef "lbox_com_port_3_baud_rate" {
            type "enumeration" {
                enum "2400 B" {
                    value "3";
                }
                enum "4800 B" {
                    value "4";
                }
                enum "9600 B" {
                    value "5";
                }
                enum "19200 B" {
                    value "6";
                }
                enum "38400 B" {
                    value "7";
                }
                enum "57600 B" {
                    value "8";
                }
                enum "115200 B" {
                    value "9";
                }
                enum "230400 B" {
                    value "10";
                }
                enum "460800 B" {
                    value "11";
                }
                enum "921600 B" {
                    value "14";
                }
            }
        }
        typedef "lbox_com_port_3_data_bits_M2" {
            type "enumeration" {
                enum "8 bits" {
                    value "1";
                }
            }
        }
        typedef "lbox_com_port_3_parity_M2" {
            type "enumeration" {
                enum "NONE" {
                    value "0";
                }
                enum "ODD" {
                    value "1";
                }
                enum "EVEN" {
                    value "2";
                }
            }
        }
        typedef "lbox_com_port_3_stop_bits_M1" {
            type "enumeration" {
                enum "1 bit" {
                    value "0";
                }
            }
        }
        typedef "lbox_term_server_type" {
            type "enumeration" {
                enum "UDP" {
                    value "0";
                }
                enum "TCP" {
                    value "1";
                }
            }
        }
        typedef "lbox_protocols_M8" {
            type "enumeration" {
                enum "None" {
                    value "0";
                }
                enum "Transparent" {
                    value "4";
                }
                enum "Async_Link" {
                    value "1";
                }
                enum "COMLI" {
                    value "14";
                }
                enum "DNP3" {
                    value "2";
                }
                enum "DF1" {
                    value "3";
                }
                enum "IEC101" {
                    value "5";
                }
                enum "Mars-A" {
                    value "13";
                }
                enum "ModbusRTU" {
                    value "8";
                }
                enum "ModbusTCP" {
                    value "9";
                }
                enum "PR2000" {
                    value "10";
                }
                enum "RDS" {
                    value "7";
                }
                enum "S3964R" {
                    value "11";
                }
                enum "SAIA_S-BUS" {
                    value "12";
                }
                enum "UNI" {
                    value "6";
                }
            }
        }
        typedef "lbox_mqtt_qos" {
            type "enumeration" {
                enum "LB_mqtt_qos_0" {
                    value "0";
                }
                enum "LB_mqtt_qos_1" {
                    value "1";
                }
                enum "LB_mqtt_qos_2" {
                    value "2";
                }
            }
        }
        typedef "lbox_mqtt_protocol_version" {
            type "enumeration" {
                enum "LB_mqtt_protocol_version_mqttv31" {
                    value "0";
                }
                enum "LB_mqtt_protocol_version_mqttv311" {
                    value "1";
                }
                enum "LB_mqtt_protocol_version_mqttv50" {
                    value "2";
                }
            }
        }
        typedef "lbox_moni_max_bandwidth" {
            type "enumeration" {
                enum "LOW" {
                    value "0";
                }
                enum "NORMAL" {
                    value "1";
                }
                enum "HIGH" {
                    value "2";
                }
                enum "UNLIMITED" {
                    value "3";
                }
            }
        }
        typedef "lbox_udp_reserved_ports" {
            type "enumeration" {
                enum "MANUAL" {
                    value "0";
                }
                enum "COM1" {
                    value "1";
                }
                enum "COM2" {
                    value "2";
                }
                enum "COM3" {
                    value "3";
                }
                enum "TS1" {
                    value "4";
                }
                enum "TS2" {
                    value "5";
                }
                enum "TS3" {
                    value "6";
                }
                enum "TS4" {
                    value "7";
                }
                enum "TS5" {
                    value "8";
                }
            }
        }
        typedef "lbox_com_prot_addr_mode" {
            type "enumeration" {
                enum "Mask" {
                    value "0";
                }
                enum "Table" {
                    value "1";
                }
            }
        }
        typedef "lbox_com_prot_mode" {
            type "enumeration" {
                enum "Master" {
                    value "0";
                }
                enum "Slave" {
                    value "1";
                }
            }
        }
        typedef "lbox_com_prot_slave_dst" {
            type "enumeration" {
                enum "LASTRCV" {
                    value "0";
                }
                enum "TARGET" {
                    value "1";
                }
            }
        }
        typedef "lbox_com_prot_mode_plus" {
            type "enumeration" {
                enum "Master" {
                    value "0";
                }
                enum "Slave" {
                    value "1";
                }
                enum "SlavePlus" {
                    value "2";
                }
            }
        }
        typedef "lbox_com_prot_saia_sbus_mode" {
            type "enumeration" {
                enum "Data" {
                    value "0";
                }
                enum "Break" {
                    value "1";
                }
            }
        }
        typedef "lbox_com_prot_auth_mode" {
            type "enumeration" {
                enum "LB_com_prot_auth_mode_None" {
                    value "0";
                }
                enum "LB_com_prot_auth_mode_PAP" {
                    value "1";
                }
                enum "LB_com_prot_auth_mode_CHAP" {
                    value "2";
                }
            }
        }
        typedef "lbox_auto_manual" {
            type "enumeration" {
                enum "LB_auto_manual_Auto" {
                    value "0";
                }
                enum "LB_auto_manual_Manual" {
                    value "1";
                }
            }
        }
        typedef "lbox_auto_limited" {
            type "enumeration" {
                enum "LB_auto_limited_V_Automatic" {
                    value "0";
                }
                enum "LB_auto_limited_V_Limited" {
                    value "1";
                }
            }
        }
        typedef "lbox_radio_fec_bdp_M9" {
            type "enumeration" {
                enum "1/1" {
                    value "0";
                }
                enum "5/6" {
                    value "1";
                }
                enum "3/4" {
                    value "2";
                }
                enum "2/3" {
                    value "3";
                }
            }
        }
        typedef "lbox_radio_fec_flex_M9" {
            type "enumeration" {
                enum "1/1" {
                    value "0";
                }
                enum "5/6" {
                    value "1";
                }
                enum "3/4" {
                    value "2";
                }
                enum "2/3" {
                    value "3";
                }
            }
        }
        typedef "lbox_cellular_network" {
            type "enumeration" {
                enum "Automatic" {
                    value "0";
                }
                enum "Prefer manual" {
                    value "1";
                }
                enum "Lock to manual" {
                    value "2";
                }
                enum "Lock to home" {
                    value "3";
                }
            }
        }
        typedef "lbox_cellular_Main_preferred_svc_M2" {
            type "enumeration" {
                enum "LB_cell_pref_svc_2g_first" {
                    value "0";
                }
                enum "LB_cell_pref_svc_2g_only" {
                    value "1";
                }
                enum "LB_cell_pref_svc_3g_first" {
                    value "2";
                }
                enum "LB_cell_pref_svc_3g_only" {
                    value "3";
                }
                enum "LB_cell_pref_svc_2g_3g_only" {
                    value "4";
                }
                enum "LB_cell_pref_svc_4g_first" {
                    value "5";
                }
                enum "LB_cell_pref_svc_4g_only" {
                    value "6";
                }
                enum "LB_cell_pref_svc_3g_4g_only" {
                    value "7";
                }
                enum "LB_cell_pref_svc_5g_only" {
                    value "8";
                }
                enum "LB_cell_pref_svc_3g_5g_only" {
                    value "9";
                }
                enum "LB_cell_pref_svc_4g_5g_only" {
                    value "10";
                }
                enum "LB_cell_pref_svc_3g_4g_5g_only" {
                    value "11";
                }
            }
        }
        typedef "lbox_cellular_authentication" {
            type "enumeration" {
                enum "None" {
                    value "0";
                }
                enum "PAP (legacy)" {
                    value "1";
                }
                enum "CHAP" {
                    value "2";
                }
            }
        }
        typedef "lbox_cellular_sim_select" {
            type "enumeration" {
                enum "SIM1" {
                    value "0";
                }
                enum "SIM2" {
                    value "1";
                }
            }
        }
        typedef "lbox_cellular_Main_preferred_svc_lpwan_M2" {
            type "enumeration" {
                enum "LB_cell_pref_svc_lpwan_Lte_cat_m_first" {
                    value "0";
                }
                enum "LB_cell_pref_svc_lpwan_Lte_cat_m_only" {
                    value "1";
                }
                enum "LB_cell_pref_svc_lpwan_Lte_cat_nb_first" {
                    value "2";
                }
                enum "LB_cell_pref_svc_lpwan_Lte_cat_nb_only" {
                    value "3";
                }
            }
        }
        typedef "lbox_cellular_Aux_preferred_svc_M2" {
            type "enumeration" {
                enum "LB_cell_pref_svc_2g_first" {
                    value "0";
                }
                enum "LB_cell_pref_svc_2g_only" {
                    value "1";
                }
                enum "LB_cell_pref_svc_3g_first" {
                    value "2";
                }
                enum "LB_cell_pref_svc_3g_only" {
                    value "3";
                }
                enum "LB_cell_pref_svc_2g_3g_only" {
                    value "4";
                }
                enum "LB_cell_pref_svc_4g_first" {
                    value "5";
                }
                enum "LB_cell_pref_svc_4g_only" {
                    value "6";
                }
                enum "LB_cell_pref_svc_3g_4g_only" {
                    value "7";
                }
                enum "LB_cell_pref_svc_5g_only" {
                    value "8";
                }
                enum "LB_cell_pref_svc_3g_5g_only" {
                    value "9";
                }
                enum "LB_cell_pref_svc_4g_5g_only" {
                    value "10";
                }
                enum "LB_cell_pref_svc_3g_4g_5g_only" {
                    value "11";
                }
            }
        }
        typedef "lbox_cellular_Aux_preferred_svc_lpwan_M2" {
            type "enumeration" {
                enum "LB_cell_pref_svc_lpwan_Lte_cat_m_first" {
                    value "0";
                }
                enum "LB_cell_pref_svc_lpwan_Lte_cat_m_only" {
                    value "1";
                }
                enum "LB_cell_pref_svc_lpwan_Lte_cat_nb_first" {
                    value "2";
                }
                enum "LB_cell_pref_svc_lpwan_Lte_cat_nb_only" {
                    value "3";
                }
            }
        }
        typedef "lbox_firewall_pol_direction" {
            type "enumeration" {
                enum "LB_firewall_pol_direction_V_In" {
                    value "0";
                }
                enum "LB_firewall_pol_direction_V_Out" {
                    value "1";
                }
            }
        }
        typedef "lbox_firewall_policy" {
            type "enumeration" {
                enum "LB_firewall_policy_V_None" {
                    value "0";
                }
                enum "LB_firewall_policy_V_IPsec" {
                    value "1";
                }
            }
        }
        typedef "lbox_l3_protocol" {
            type "enumeration" {
                enum "All" {
                    value "0";
                }
                enum "ICMP" {
                    value "1";
                }
                enum "UDP" {
                    value "2";
                }
                enum "TCP" {
                    value "3";
                }
                enum "GRE" {
                    value "4";
                }
                enum "ESP" {
                    value "5";
                }
                enum "Other" {
                    value "6";
                }
            }
        }
        typedef "lbox_network_devices_log_M8" {
            type "enumeration" {
                enum "All" {
                    value "0";
                }
                enum "Radio" {
                    value "1";
                }
                enum "WWAN" {
                    value "7";
                }
                enum "All ETH" {
                    value "2";
                }
                enum "EXT" {
                    value "5";
                }
                enum "All PPP" {
                    value "8";
                }
                enum "PPPoE client" {
                    value "10";
                }
                enum "GRE L3" {
                    value "6";
                }
                enum "OpenVPN L3" {
                    value "9";
                }
                enum "HotStandby" {
                    value "3";
                }
                enum "Other" {
                    value "4";
                }
            }
        }
        typedef "lbox_firewall_action" {
            type "enumeration" {
                enum "Deny" {
                    value "0";
                }
                enum "Allow" {
                    value "1";
                }
            }
        }
        typedef "lbox_network_devices_log_phy_M9" {
            type "enumeration" {
                enum "All" {
                    value "0";
                }
                enum "Radio" {
                    value "1";
                }
                enum "WWAN" {
                    value "13";
                }
                enum "All ETH" {
                    value "2";
                }
                enum "EXT" {
                    value "10";
                }
                enum "ETH1" {
                    value "3";
                }
                enum "ETH2" {
                    value "4";
                }
                enum "ETH3" {
                    value "5";
                }
                enum "ETH4" {
                    value "6";
                }
                enum "ETH5" {
                    value "7";
                }
                enum "All PPP" {
                    value "14";
                }
                enum "PPPoE client" {
                    value "17";
                }
                enum "GRE L2" {
                    value "11";
                }
                enum "GRE L3" {
                    value "12";
                }
                enum "OpenVPN L2" {
                    value "15";
                }
                enum "OpenVPN L3" {
                    value "16";
                }
                enum "HotStandby" {
                    value "8";
                }
                enum "Other" {
                    value "9";
                }
            }
        }
        typedef "lbox_net_services" {
            type "enumeration" {
                enum "Other" {
                    value "0";
                }
                enum "COM1" {
                    value "1";
                }
                enum "COM2" {
                    value "2";
                }
                enum "COM3" {
                    value "3";
                }
                enum "TS1" {
                    value "4";
                }
                enum "TS2" {
                    value "5";
                }
                enum "TS3" {
                    value "6";
                }
                enum "TS4" {
                    value "7";
                }
                enum "TS5" {
                    value "8";
                }
                enum "SSH" {
                    value "9";
                }
                enum "HTTP" {
                    value "10";
                }
                enum "HTTPS" {
                    value "11";
                }
                enum "Remote access" {
                    value "12";
                }
                enum "SNMP" {
                    value "13";
                }
                enum "NTP" {
                    value "14";
                }
            }
        }
        typedef "lbox_l2_protocol" {
            type "enumeration" {
                enum "LB_l2_protocol_V_All" {
                    value "0";
                }
                enum "LB_l2_protocol_V_Not_VLAN" {
                    value "1";
                }
                enum "LB_l2_protocol_V_All_VLAN" {
                    value "2";
                }
                enum "LB_l2_protocol_V_IPv4" {
                    value "3";
                }
                enum "LB_l2_protocol_V_IPv6" {
                    value "4";
                }
                enum "LB_l2_protocol_V_ARP" {
                    value "5";
                }
                enum "LB_l2_protocol_V_Other" {
                    value "6";
                }
            }
        }
        typedef "lbox_l2_address_filter" {
            type "enumeration" {
                enum "LB_l2_address_filter_V_All" {
                    value "0";
                }
                enum "LB_l2_address_filter_V_Mask" {
                    value "1";
                }
                enum "LB_l2_address_filter_V_Unicasts" {
                    value "2";
                }
                enum "LB_l2_address_filter_V_Multicasts" {
                    value "3";
                }
                enum "LB_l2_address_filter_V_Broadcasts" {
                    value "4";
                }
            }
        }
        typedef "lbox_network_devices_phy" {
            type "enumeration" {
                enum "All" {
                    value "0";
                }
                enum "Radio" {
                    value "1";
                }
                enum "All ETH" {
                    value "2";
                }
                enum "ETH1" {
                    value "3";
                }
                enum "ETH2" {
                    value "4";
                }
                enum "ETH3" {
                    value "5";
                }
                enum "ETH4" {
                    value "6";
                }
                enum "ETH5" {
                    value "7";
                }
                enum "GRE L2" {
                    value "8";
                }
                enum "OpenVPN L2" {
                    value "9";
                }
                enum "Other" {
                    value "10";
                }
            }
        }
        typedef "lbox_qos_priority" {
            type "enumeration" {
                enum "1 (Highest)" {
                    value "0";
                }
                enum "2" {
                    value "1";
                }
                enum "3" {
                    value "2";
                }
                enum "4" {
                    value "3";
                }
                enum "5" {
                    value "4";
                }
                enum "6" {
                    value "5";
                }
                enum "7" {
                    value "6";
                }
                enum "8 (Lowest)" {
                    value "7";
                }
            }
        }
        typedef "lbox_qos_flow_label" {
            type "enumeration" {
                enum "Flow_A" {
                    value "0";
                }
                enum "Flow_B" {
                    value "1";
                }
                enum "Flow_C" {
                    value "2";
                }
                enum "Flow_D" {
                    value "3";
                }
                enum "Flow_E" {
                    value "4";
                }
                enum "Flow_F" {
                    value "5";
                }
                enum "Flow_G" {
                    value "6";
                }
                enum "Flow_H" {
                    value "7";
                }
            }
        }
        typedef "lbox_qos_rate_unit" {
            type "enumeration" {
                enum "kibps" {
                    value "1";
                }
                enum "Mibps" {
                    value "2";
                }
            }
        }
        typedef "lbox_qos_ds_type" {
            type "enumeration" {
                enum "Off" {
                    value "0";
                }
                enum "DSCP" {
                    value "1";
                }
                enum "TOS_Precedence" {
                    value "2";
                }
            }
        }
        typedef "lbox_qos_target" {
            type "enumeration" {
                enum "Flow_A_Prio_1_Highest" {
                    value "0";
                }
                enum "Flow_B_Prio_2" {
                    value "1";
                }
                enum "Flow_C_Prio_3" {
                    value "2";
                }
                enum "Flow_D_Prio_4" {
                    value "3";
                }
                enum "Flow_E_Prio_5" {
                    value "4";
                }
                enum "Flow_F_Prio_6" {
                    value "5";
                }
                enum "Flow_G_Prio_7" {
                    value "6";
                }
                enum "Flow_H_Prio_8_Lowest" {
                    value "7";
                }
            }
        }
        typedef "lbox_dhcp_srv_announce" {
            type "enumeration" {
                enum "LB_dhcp_srv_announce_V_Off" {
                    value "0";
                }
                enum "LB_dhcp_srv_announce_V_Local" {
                    value "1";
                }
                enum "LB_dhcp_srv_announce_V_Manual" {
                    value "2";
                }
            }
        }
        typedef "lbox_ospf_metric_type" {
            type "enumeration" {
                enum "Type 1" {
                    value "0";
                }
                enum "Type 2" {
                    value "1";
                }
            }
        }
        typedef "lbox_adr_filter_match" {
            type "enumeration" {
                enum "Off" {
                    value "0";
                }
                enum "Match" {
                    value "1";
                }
                enum "Not match" {
                    value "2";
                }
            }
        }
        typedef "lbox_ospf_source" {
            type "enumeration" {
                enum "Internal" {
                    value "0";
                }
                enum "Inter-area" {
                    value "1";
                }
                enum "External type 1" {
                    value "2";
                }
                enum "External type 2" {
                    value "3";
                }
            }
        }
        typedef "lbox_adr_filter_action" {
            type "enumeration" {
                enum "Accept" {
                    value "0";
                }
                enum "Reject" {
                    value "1";
                }
                enum "Pass" {
                    value "2";
                }
            }
        }
        typedef "lbox_adr_filter_bgppath_simple" {
            type "enumeration" {
                enum "Off" {
                    value "0";
                }
                enum "Is empty" {
                    value "1";
                }
                enum "Not empty" {
                    value "2";
                }
            }
        }
        typedef "lbox_adr_filter_bgppath_full" {
            type "enumeration" {
                enum "Off" {
                    value "0";
                }
                enum "Is empty" {
                    value "1";
                }
                enum "Not empty" {
                    value "2";
                }
                enum "Contain" {
                    value "3";
                }
                enum "Not contain" {
                    value "4";
                }
            }
        }
        typedef "lbox_adr_filter_bgppath_pos" {
            type "enumeration" {
                enum "Any" {
                    value "0";
                }
                enum "Neighbor" {
                    value "1";
                }
                enum "Source" {
                    value "2";
                }
            }
        }
        typedef "lbox_adr_filter_metric_cmp" {
            type "enumeration" {
                enum "Off" {
                    value "0";
                }
                enum "<" {
                    value "1";
                }
                enum "<=" {
                    value "2";
                }
                enum ">=" {
                    value "3";
                }
                enum ">" {
                    value "4";
                }
            }
        }
        typedef "lbox_test_2_evaluation" {
            type "enumeration" {
                enum "LB_CellLT_ProfileSwitch_One_succeeds" {
                    value "0";
                }
                enum "LB_CellLT_ProfileSwitch_Both_succeed" {
                    value "1";
                }
            }
        }
        typedef "lbox_ipsec_integrity" {
            type "enumeration" {
                enum "MD5 (legacy)" {
                    value "0";
                }
                enum "SHA1 (legacy)" {
                    value "1";
                }
                enum "SHA256" {
                    value "2";
                }
                enum "SHA384" {
                    value "3";
                }
                enum "SHA512" {
                    value "4";
                }
            }
        }
        typedef "lbox_IpSecA_IKE_Encryption_M1" {
            type "enumeration" {
                enum "3DES (legacy)" {
                    value "0";
                }
                enum "AES128" {
                    value "1";
                }
                enum "AES192" {
                    value "2";
                }
                enum "AES256" {
                    value "3";
                }
                enum "AES128CCM (AEAD)" {
                    value "4";
                }
                enum "AES192CCM (AEAD)" {
                    value "5";
                }
                enum "AES256CCM (AEAD)" {
                    value "6";
                }
                enum "AES128GCM (AEAD)" {
                    value "7";
                }
                enum "AES192GCM (AEAD)" {
                    value "8";
                }
                enum "AES256GCM (AEAD)" {
                    value "9";
                }
                enum "ChaCha20Poly1305 (AEAD)" {
                    value "10";
                }
            }
        }
        typedef "lbox_IpSecA_IKE_AEAD_ICV" {
            type "enumeration" {
                enum "64b" {
                    value "0";
                }
                enum "96b" {
                    value "1";
                }
                enum "128b" {
                    value "2";
                }
            }
        }
        typedef "lbox_ipsec_leak_prevention" {
            type "enumeration" {
                enum "LB_ipsec_leak_prevention_V_Off" {
                    value "0";
                }
                enum "LB_ipsec_leak_prevention_V_Exact" {
                    value "1";
                }
                enum "LB_ipsec_leak_prevention_V_Paranoid" {
                    value "2";
                }
            }
        }
        typedef "lbox_openvpn_protocol" {
            type "enumeration" {
                enum "UDP" {
                    value "0";
                }
                enum "TCP" {
                    value "1";
                }
            }
        }
        typedef "lbox_openvpn_tls_protection_mode" {
            type "enumeration" {
                enum "LB_openvpn_tls_protection_mode_Off" {
                    value "0";
                }
                enum "LB_openvpn_tls_protection_mode_TLS_Auth" {
                    value "1";
                }
                enum "LB_openvpn_tls_protection_mode_TLS_Crypt" {
                    value "2";
                }
            }
        }
        typedef "lbox_openvpn_tlsauth_key_dir" {
            type "enumeration" {
                enum "0" {
                    value "0";
                }
                enum "1" {
                    value "1";
                }
            }
        }
        typedef "lbox_mqtt_direction" {
            type "enumeration" {
                enum "LB_mqtt_direction_in" {
                    value "0";
                }
                enum "LB_mqtt_direction_out" {
                    value "1";
                }
                enum "LB_mqtt_direction_both" {
                    value "2";
                }
            }
        }
        typedef "lim_Event_Radio_Temp_Low_Hyst_M2" {
            type "uint8" {
                range "1..10";
            }
        }
        typedef "lim_uint_8_1toFF" {
            type "uint8" {
                range "1..255";
            }
        }
        typedef "lim_ipv4_mask" {
            type "uint8" {
                range "1..32";
            }
        }
        typedef "lim_babelflt_rss" {
            type "uint8" {
                range "50..150";
            }
        }
        typedef "lim_babelflt_mse" {
            type "uint8" {
                range "0..60";
            }
        }
        typedef "lim_RadioFreqTx_M3" {
            type "uint32" {
                range "100000000..999999999";
            }
        }
        typedef "lim_radio_retries" {
            type "uint8" {
                range "0..15";
            }
        }
        typedef "lim_uint_8" {
            type "uint8" {
                range "0..255";
            }
        }
        typedef "lim_udp_port" {
            type "uint16" {
                range "1..65535";
            }
        }
        typedef "lim_fwall_traffic_filter" {
            type "uint16" {
                range "1..10000";
            }
        }
        typedef "lim_routing_metric_dyn" {
            type "uint32" {
                range "1..4294967294";
            }
        }
        typedef "lim_uint_32" {
            type "uint32" {
                range "0..4294967295";
            }
        }
        typedef "lim_uint_16_1toFF" {
            type "uint16" {
                range "1..65535";
            }
        }
        typedef "lim_adr_babel_metric" {
            type "uint16" {
                range "1..65534";
            }
        }
        typedef "lim_ipv4_mask0" {
            type "uint8" {
                range "0..32";
            }
        }
        typedef "lim_uint_16" {
            type "uint16" {
                range "0..65535";
            }
        }
        typedef "lim_time_hours_day" {
            type "uint8" {
                range "0..23";
            }
        }
        typedef "lim_time_minutes_hr" {
            type "uint8" {
                range "0..59";
            }
        }
        typedef "lim_unpriv_port" {
            type "uint16" {
                range "1024..65535";
            }
        }
        typedef "lim_udp_port0" {
            type "uint16" {
                range "0..65535";
            }
        }
        typedef "lim_qos_dscp" {
            type "uint8" {
                range "0..63";
            }
        }
        typedef "lim_vlan_id" {
            type "uint16" {
                range "0..4094";
            }
        }
        typedef "lim_qos_rate_limit" {
            type "uint16" {
                range "1..10000";
            }
        }
        typedef "lim_qos_tos_precedence" {
            type "uint8" {
                range "0..7";
            }
        }
        typedef "lim_qos_vlan_priority" {
            type "uint8" {
                range "0..7";
            }
        }
        typedef "lim_l4_port_mask" {
            type "uint8" {
                range "0..16";
            }
        }
        typedef "lim_routing_metric" {
            type "uint32" {
                range "0..4294967294";
            }
        }
        typedef "lim_adr_metric" {
            type "uint16" {
                range "1..65535";
            }
        }
        typedef "lim_adr_preference" {
            type "uint16" {
                range "0..65535";
            }
        }
        typedef "lim_adr_babel_metric0" {
            type "uint16" {
                range "0..65534";
            }
        }
        typedef "lim_openvpn_link_frag_size" {
            type "uint16" {
                range "70..1500";
            }
        }
        grouping "SerialProtocol" {
            choice "ch-SerialProtocol" {
                case "c-None" {
                    when "deref(./_variant_source_ref) = \"None\"";
                }
                case "c-Async_Link" {
                    when "deref(./_variant_source_ref) = \"Async_Link\"";
                    container "Async_Link" {
                        container "Protocol_AsyncLink" {
                            leaf "RR_ComProt_DstIP" {
                                type "inet:ipv4-address";
                            }
                            leaf "RR_ComProt_DstPort" {
                                when "not (./../../Protocol_AsyncLink/RR_ComProt_DstStdPort != 'MANUAL')";
                                type "lim_udp_port0";
                            }
                            leaf "RR_ComProt_DstStdPort" {
                                type "lbox_udp_reserved_ports";
                            }
                            leaf "RR_ComProt_AsyncBcastAll" {
                                when "not (/config_data/device/DeviceHw/RR_DynHw_Primary_Radio != 'On')";
                                type "lbox_off_on";
                            }
                            leaf "RR_ComProt_AsyncBcastRx" {
                                when "not (/config_data/device/DeviceHw/RR_DynHw_Primary_Radio != 'On')";
                                type "lbox_off_on";
                            }
                        }
                    }
                }
                case "c-DNP3" {
                    when "deref(./_variant_source_ref) = \"DNP3\"";
                    container "DNP3" {
                        container "Protocol_DNP3" {
                            leaf "RR_ComProt_DNP3_AtrmIpBase" {
                                when "not (./../../Protocol_DNP3/RR_ComProt_DNP3_AtrMethod = 'Table')";
                                type "inet:ipv4-address";
                            }
                            leaf "RR_ComProt_DNP3_AtrmUdpPort" {
                                when "not ((./../../Protocol_DNP3/RR_ComProt_DNP3_AtrMethod = 'Table') or (./../../Protocol_DNP3/RR_ComProt_DNP3_DstStdPort != 'MANUAL'))";
                                type "lim_udp_port";
                            }
                            leaf "RR_ComProt_DNP3_AtrMethod" {
                                type "lbox_com_prot_addr_mode";
                            }
                            leaf "RR_ComProt_DNP3_AtrmIpMask" {
                                when "not (./../../Protocol_DNP3/RR_ComProt_DNP3_AtrMethod = 'Table')";
                                type "lim_ipv4_mask";
                            }
                            leaf "RR_ComProt_DNP3_DstStdPort" {
                                when "not (./../../Protocol_DNP3/RR_ComProt_DNP3_AtrMethod = 'Table')";
                                type "lbox_udp_reserved_ports";
                            }
                            leaf "RR_ComProt_DNP3_Bcast" {
                                when "not (/config_data/device/DeviceHw/RR_DynHw_Primary_Radio != 'On')";
                                type "lbox_off_on";
                            }
                        }
                        list "RR_S_TABLE_Protocol_DNP3_TTable" {
                            when "not (./../Protocol_DNP3/RR_ComProt_DNP3_AtrMethod = 'Mask')";
                            key "ID";
                            max-elements "1024";
                            ordered-by "user";
                            leaf "ID" {
                                type "lim_uint_16";
                            }
                            leaf "TTEntry_DNP3_Ena" {
                                type "lbox_off_on";
                                default "On";
                            }
                            leaf "TTEntry_DNP3_Note" {
                                type "string" {
                                    pattern "[^\"`\\\\$;]{0,42}";
                                }
                                default "";
                            }
                            leaf "TTEntry_DNP3_DevAddr_2B" {
                                type "lim_uint_16";
                                must ". <= ../TTEntry_DNP3_DevAddrLast_2B" {
                                    error-message "valmsg_it_TTEntry_DNP3_DevAddr_2B";
                                }
                                default "1";
                            }
                            leaf "TTEntry_DNP3_DevAddrLast_2B" {
                                type "lim_uint_16";
                                must ". >= ../TTEntry_DNP3_DevAddr_2B" {
                                    error-message "valmsg_it_TTEntry_DNP3_DevAddrLast_2B";
                                }
                                default "1";
                            }
                            leaf "TTEntry_DNP3_IpAddr" {
                                type "inet:ipv4-address";
                                default "0.0.0.0";
                            }
                            leaf "TTEntry_DNP3_IpInt" {
                                type "lbox_off_on";
                                default "Off";
                            }
                            leaf "TTEntry_DNP3_StdPort" {
                                type "lbox_udp_reserved_ports";
                                default "COM1";
                            }
                            leaf "TTEntry_DNP3_ManPort" {
                                when "not (../TTEntry_DNP3_StdPort != 'MANUAL')";
                                type "lim_udp_port";
                                default "50000";
                            }
                        }
                    }
                }
                case "c-DF1" {
                    when "deref(./_variant_source_ref) = \"DF1\"";
                    container "DF1" {
                        container "Protocol_DF1" {
                            leaf "RR_ComProt_DF1_AtrMethod" {
                                type "lbox_com_prot_addr_mode";
                            }
                            leaf "RR_ComProt_DF1_Mode" {
                                when "not (./../../Protocol_DF1/RR_ComProt_DF1_DuplexMode = 'Full duplex')";
                                type "lbox_com_prot_mode";
                            }
                            leaf "RR_ComProt_DF1_ChecksumMode" {
                                type "enumeration" {
                                    enum "BCC" {
                                        value "0";
                                    }
                                    enum "CRC" {
                                        value "1";
                                    }
                                }
                            }
                            leaf "RR_ComProt_DF1_DuplexMode" {
                                type "enumeration" {
                                    enum "Full duplex" {
                                        value "0";
                                    }
                                    enum "Half duplex" {
                                        value "1";
                                    }
                                }
                                must "not ((. = 'Half duplex' and (/config_data/auth/CnfAuth/RR_CnfAuthCnfVersion >= 0)))";
                            }
                            leaf "RR_ComProt_DF1_Bcast" {
                                when "not (/config_data/device/DeviceHw/RR_DynHw_Primary_Radio != 'On')";
                                type "lbox_off_on";
                            }
                            leaf "RR_ComProt_DF1_AtrmIpBase" {
                                when "not (./../../Protocol_DF1/RR_ComProt_DF1_AtrMethod = 'Table')";
                                type "inet:ipv4-address";
                            }
                            leaf "RR_ComProt_DF1_AtrmUdpPort" {
                                when "not ((./../../Protocol_DF1/RR_ComProt_DF1_AtrMethod = 'Table') or (./../../Protocol_DF1/RR_ComProt_DF1_DstStdPort != 'MANUAL'))";
                                type "lim_udp_port";
                            }
                            leaf "RR_ComProt_DF1_AtrmIpMask" {
                                when "not (./../../Protocol_DF1/RR_ComProt_DF1_AtrMethod = 'Table')";
                                type "lim_ipv4_mask";
                            }
                            leaf "RR_ComProt_DF1_DstStdPort" {
                                when "not (./../../Protocol_DF1/RR_ComProt_DF1_AtrMethod = 'Table')";
                                type "lbox_udp_reserved_ports";
                            }
                            leaf "RR_ComProt_DF1_LocAckEna" {
                                type "lbox_off_on";
                            }
                            leaf "RR_ComProt_DF1_Repeats" {
                                when "not (./../../Protocol_DF1/RR_ComProt_DF1_LocAckEna != 'On')";
                                type "uint8" {
                                    range "0..31";
                                }
                            }
                            leaf "RR_ComProt_DF1_AckTimeout" {
                                when "not (./../../Protocol_DF1/RR_ComProt_DF1_LocAckEna != 'On')";
                                type "uint16" {
                                    range "0..16383";
                                }
                            }
                        }
                        list "RR_S_TABLE_Protocol_DF1_TTable" {
                            when "not (./../Protocol_DF1/RR_ComProt_DF1_AtrMethod = 'Mask')";
                            key "ID";
                            max-elements "1024";
                            ordered-by "user";
                            leaf "ID" {
                                type "lim_uint_16";
                            }
                            leaf "TTEntry_DF1_Ena" {
                                type "lbox_off_on";
                                default "On";
                            }
                            leaf "TTEntry_DF1_Note" {
                                type "string" {
                                    pattern "[^\"`\\\\$;]{0,42}";
                                }
                                default "";
                            }
                            leaf "TTEntry_DF1_DevAddr_1B" {
                                type "lim_uint_8";
                                must ". <= ../TTEntry_DF1_DevAddrLast_1B" {
                                    error-message "valmsg_it_TTEntry_DF1_DevAddr";
                                }
                                default "1";
                            }
                            leaf "TTEntry_DF1_DevAddrLast_1B" {
                                type "lim_uint_8";
                                must ". >= ../TTEntry_DF1_DevAddr_1B" {
                                    error-message "valmsg_it_TTEntry_DF1_DevAddrLast";
                                }
                                default "1";
                            }
                            leaf "TTEntry_DF1_IpAddr" {
                                type "inet:ipv4-address";
                                default "0.0.0.0";
                            }
                            leaf "TTEntry_DF1_IpInt" {
                                type "lbox_off_on";
                                default "Off";
                            }
                            leaf "TTEntry_DF1_StdPort" {
                                type "lbox_udp_reserved_ports";
                                default "COM1";
                            }
                            leaf "TTEntry_DF1_ManPort" {
                                when "not (../TTEntry_DF1_StdPort != 'MANUAL')";
                                type "lim_udp_port";
                                default "50000";
                            }
                        }
                    }
                }
                case "c-Transparent" {
                    when "deref(./_variant_source_ref) = \"Transparent\"";
                }
                case "c-IEC101" {
                    when "deref(./_variant_source_ref) = \"IEC101\"";
                    container "IEC101" {
                        container "Protocol_IEC101" {
                            leaf "RR_ComProt_IEC101_Mode" {
                                type "enumeration" {
                                    enum "Primary" {
                                        value "0";
                                    }
                                    enum "Secondary" {
                                        value "1";
                                    }
                                    enum "Combined" {
                                        value "2";
                                    }
                                }
                                must "not ((. = 'Combined' and (/config_data/auth/CnfAuth/RR_CnfAuthCnfVersion >= 0)))";
                            }
                            leaf "RR_ComProt_IEC101_AddrMode" {
                                type "enumeration" {
                                    enum "8bit" {
                                        value "0";
                                    }
                                    enum "16bit" {
                                        value "1";
                                    }
                                    enum "8bit w/o ctrl byte" {
                                        value "2";
                                    }
                                    enum "8bit swp ctrl byte" {
                                        value "3";
                                    }
                                    enum "No addr" {
                                        value "4";
                                    }
                                }
                                must "not ((. = 'No addr' and (./../../Protocol_IEC101/RR_ComProt_IEC101_Mode != 'Combined')))";
                            }
                            leaf "RR_ComProt_IEC101_Bcast" {
                                when "not (/config_data/device/DeviceHw/RR_DynHw_Primary_Radio != 'On')";
                                type "lbox_off_on";
                            }
                            leaf "RR_ComProt_IEC101_AtrmIpBase" {
                                when "not ((./../../Protocol_IEC101/RR_ComProt_IEC101_AtrMethod = 'Table') or (./../../Protocol_IEC101/RR_ComProt_IEC101_Mode = 'Secondary'))";
                                type "inet:ipv4-address";
                            }
                            leaf "RR_ComProt_IEC101_AtrmUdpPort" {
                                when "not (((./../../Protocol_IEC101/RR_ComProt_IEC101_Mode != 'Secondary') and ((./../../Protocol_IEC101/RR_ComProt_IEC101_AtrMethod = 'Table') or (./../../Protocol_IEC101/RR_ComProt_IEC101_DstStdPort != 'MANUAL'))) or ((./../../Protocol_IEC101/RR_ComProt_IEC101_Mode != 'Primary') and ((./../../Protocol_IEC101/RR_ComProt_IEC101_SlaveDst = 'LASTRCV') or (./../../Protocol_IEC101/RR_ComProt_IEC101_DstStdPort != 'MANUAL'))))";
                                type "lim_udp_port";
                            }
                            leaf "RR_ComProt_IEC101_AtrMethod" {
                                when "not (./../../Protocol_IEC101/RR_ComProt_IEC101_Mode = 'Secondary')";
                                type "lbox_com_prot_addr_mode";
                            }
                            leaf "RR_ComProt_IEC101_AtrmIpMask" {
                                when "not ((./../../Protocol_IEC101/RR_ComProt_IEC101_AtrMethod = 'Table') or (./../../Protocol_IEC101/RR_ComProt_IEC101_Mode = 'Secondary'))";
                                type "lim_ipv4_mask";
                            }
                            leaf "RR_ComProt_IEC101_DstStdPort" {
                                when "not (((./../../Protocol_IEC101/RR_ComProt_IEC101_Mode = 'Primary') and (./../../Protocol_IEC101/RR_ComProt_IEC101_AtrMethod = 'Table')) or ((./../../Protocol_IEC101/RR_ComProt_IEC101_Mode = 'Secondary') and (./../../Protocol_IEC101/RR_ComProt_IEC101_SlaveDst = 'LASTRCV')))";
                                type "lbox_udp_reserved_ports";
                            }
                            leaf "RR_ComProt_IEC101_SlaveDst" {
                                when "not (./../../Protocol_IEC101/RR_ComProt_IEC101_Mode = 'Primary')";
                                type "lbox_com_prot_slave_dst";
                            }
                            leaf "RR_ComProt_IEC101_TsDropBcast" {
                                when "not ((./../../Protocol_IEC101/RR_ComProt_IEC101_Mode != 'Primary') or (./../../Protocol_IEC101/RR_ComProt_IEC101_Bcast != 'On') or (./../../Protocol_IEC101/RR_ComProt_IEC101_AddrMode = '8bit w/o ctrl byte'))";
                                type "lbox_off_on";
                            }
                            leaf "RR_ComProt_IEC101_TsEnable" {
                                when "not ((./../../Protocol_IEC101/RR_ComProt_IEC101_Mode != 'Secondary') or (./../../Protocol_IEC101/RR_ComProt_IEC101_AddrMode = '8bit w/o ctrl byte'))";
                                type "lbox_off_on";
                            }
                            leaf "RR_ComProt_IEC101_SpEnable" {
                                when "not ((./../../Protocol_IEC101/RR_ComProt_IEC101_Mode != 'Secondary') or (./../../Protocol_IEC101/RR_ComProt_IEC101_AddrMode = '8bit w/o ctrl byte'))";
                                type "lbox_off_on";
                            }
                            leaf "RR_ComProt_IEC101_SlaveTargetIp" {
                                when "not ((./../../Protocol_IEC101/RR_ComProt_IEC101_Mode = 'Primary') or ((./../../Protocol_IEC101/RR_ComProt_IEC101_Mode = 'Secondary') and (./../../Protocol_IEC101/RR_ComProt_IEC101_SlaveDst = 'LASTRCV')))";
                                type "inet:ipv4-address";
                            }
                            leaf "RR_ComProt_IEC101_UsedProtAddr" {
                                when "not ((./../../Protocol_IEC101/RR_ComProt_IEC101_Mode != 'Secondary') or (./../../Protocol_IEC101/RR_ComProt_IEC101_AddrMode = '8bit w/o ctrl byte') or ((./../../Protocol_IEC101/RR_ComProt_IEC101_TsEnable != 'On') and (./../../Protocol_IEC101/RR_ComProt_IEC101_SpEnable != 'On')))";
                                type "lim_uint_16";
                            }
                            leaf "RR_ComProt_IEC101_SlaveId" {
                                when "not ((./../../Protocol_IEC101/RR_ComProt_IEC101_Mode != 'Secondary') or (./../../Protocol_IEC101/RR_ComProt_IEC101_AddrMode = '8bit w/o ctrl byte') or (./../../Protocol_IEC101/RR_ComProt_IEC101_SpEnable != 'On'))";
                                type "lim_uint_8";
                            }
                            leaf "RR_ComProt_IEC101_SubgroupId" {
                                when "not ((./../../Protocol_IEC101/RR_ComProt_IEC101_Mode != 'Secondary') or (./../../Protocol_IEC101/RR_ComProt_IEC101_AddrMode = '8bit w/o ctrl byte') or (./../../Protocol_IEC101/RR_ComProt_IEC101_SpEnable != 'On'))";
                                type "lim_uint_8";
                            }
                            leaf "RR_ComProt_IEC101_SpPollPeriod" {
                                when "not ((./../../Protocol_IEC101/RR_ComProt_IEC101_Mode != 'Secondary') or (./../../Protocol_IEC101/RR_ComProt_IEC101_AddrMode = '8bit w/o ctrl byte') or (./../../Protocol_IEC101/RR_ComProt_IEC101_SpEnable != 'On'))";
                                type "uint16" {
                                    range "10..60000";
                                }
                            }
                            leaf "RR_ComProt_IEC101_SpTsPeriod" {
                                when "not ((./../../Protocol_IEC101/RR_ComProt_IEC101_Mode != 'Secondary') or (./../../Protocol_IEC101/RR_ComProt_IEC101_AddrMode = '8bit w/o ctrl byte') or (./../../Protocol_IEC101/RR_ComProt_IEC101_SpEnable != 'On') or (./../../Protocol_IEC101/RR_ComProt_IEC101_TsEnable != 'On'))";
                                type "lim_uint_8";
                            }
                            leaf "RR_ComProt_IEC101_NetRepeatTime" {
                                when "not ((./../../Protocol_IEC101/RR_ComProt_IEC101_Mode != 'Secondary') or (./../../Protocol_IEC101/RR_ComProt_IEC101_AddrMode = '8bit w/o ctrl byte') or (./../../Protocol_IEC101/RR_ComProt_IEC101_SpEnable != 'On'))";
                                type "uint16" {
                                    range "10..60000";
                                }
                            }
                            leaf "RR_ComProt_IEC101_PortRepeatTime" {
                                when "not ((./../../Protocol_IEC101/RR_ComProt_IEC101_Mode != 'Secondary') or (./../../Protocol_IEC101/RR_ComProt_IEC101_AddrMode = '8bit w/o ctrl byte') or ((./../../Protocol_IEC101/RR_ComProt_IEC101_TsEnable != 'On') and (./../../Protocol_IEC101/RR_ComProt_IEC101_SpEnable != 'On')))";
                                type "uint16" {
                                    range "10..60000";
                                }
                            }
                            leaf "RR_ComProt_IEC101_PortRepeatCount" {
                                when "not ((./../../Protocol_IEC101/RR_ComProt_IEC101_Mode != 'Secondary') or (./../../Protocol_IEC101/RR_ComProt_IEC101_AddrMode = '8bit w/o ctrl byte') or ((./../../Protocol_IEC101/RR_ComProt_IEC101_TsEnable != 'On') and (./../../Protocol_IEC101/RR_ComProt_IEC101_SpEnable != 'On')))";
                                type "lim_uint_8";
                            }
                        }
                        list "RR_S_TABLE_Protocol_IEC101_TTable" {
                            when "not ((./../Protocol_IEC101/RR_ComProt_IEC101_AtrMethod = 'Mask') or (./../Protocol_IEC101/RR_ComProt_IEC101_Mode = 'Secondary'))";
                            key "ID";
                            max-elements "1024";
                            ordered-by "user";
                            leaf "ID" {
                                type "lim_uint_16";
                            }
                            leaf "TTEntry_IEC101_Ena" {
                                type "lbox_off_on";
                                default "On";
                            }
                            leaf "TTEntry_IEC101_Note" {
                                type "string" {
                                    pattern "[^\"`\\\\$;]{0,42}";
                                }
                                default "";
                            }
                            leaf "TTEntry_IEC101_DevAddr_2B" {
                                type "lim_uint_16";
                                must ". <= ../TTEntry_IEC101_DevAddrLast_2B" {
                                    error-message "valmsg_it_TTEntry_IEC101_DevAddr_2B";
                                }
                                default "1";
                            }
                            leaf "TTEntry_IEC101_DevAddrLast_2B" {
                                type "lim_uint_16";
                                must ". >= ../TTEntry_IEC101_DevAddr_2B" {
                                    error-message "valmsg_it_TTEntry_IEC101_DevAddr_2B";
                                }
                                default "1";
                            }
                            leaf "TTEntry_IEC101_IpAddr" {
                                type "inet:ipv4-address";
                                default "0.0.0.0";
                            }
                            leaf "TTEntry_IEC101_IpInt" {
                                type "lbox_off_on";
                                default "Off";
                            }
                            leaf "TTEntry_IEC101_StdPort" {
                                type "lbox_udp_reserved_ports";
                                default "COM1";
                            }
                            leaf "TTEntry_IEC101_ManPort" {
                                when "not (../TTEntry_IEC101_StdPort != 'MANUAL')";
                                type "lim_udp_port";
                                default "50000";
                            }
                        }
                    }
                }
                case "c-UNI" {
                    when "deref(./_variant_source_ref) = \"UNI\"";
                    container "UNI" {
                        container "Protocol_UNI" {
                            leaf "RR_ComProt_UNI_PollResponseCtrl" {
                                when "not (./../../Protocol_UNI/RR_ComProt_UNI_Mode != 'Master')";
                                type "lbox_off_on";
                            }
                            leaf "RR_ComProt_UNI_Mode" {
                                type "lbox_com_prot_mode";
                            }
                            leaf "RR_ComProt_UNI_AddrMode" {
                                when "not (./../../Protocol_UNI/RR_ComProt_UNI_Mode != 'Master')";
                                type "enumeration" {
                                    enum "bin_1B" {
                                        value "0";
                                    }
                                    enum "ascii_2B" {
                                        value "1";
                                    }
                                    enum "bin_2B_LSB" {
                                        value "2";
                                    }
                                    enum "bin_2B_MSB" {
                                        value "3";
                                    }
                                }
                            }
                            leaf "RR_ComProt_UNI_Bcast" {
                                when "not (/config_data/device/DeviceHw/RR_DynHw_Primary_Radio != 'On')";
                                type "lbox_off_on";
                            }
                            leaf "RR_ComProt_UNI_AddrPos" {
                                when "not (./../../Protocol_UNI/RR_ComProt_UNI_Mode != 'Master')";
                                type "lim_uint_8_1toFF";
                            }
                            leaf "RR_ComProt_UNI_AddressMask" {
                                when "not ((./../../Protocol_UNI/RR_ComProt_UNI_Mode != 'Master') or (./../../Protocol_UNI/RR_ComProt_UNI_AddrMode = 'bin_1B' and ./../../Protocol_UNI/RR_ComProt_UNI_AddrMode = 'ascii_2B'))";
                                type "lim_uint_16";
                            }
                            leaf "RR_ComProt_UNI_BcastAddress" {
                                when "not ((/config_data/device/DeviceHw/RR_DynHw_Primary_Radio != 'On') or (./../../Protocol_UNI/RR_ComProt_UNI_Mode != 'Master') or (./../../Protocol_UNI/RR_ComProt_UNI_Bcast != 'On'))";
                                type "lim_uint_16";
                            }
                            leaf "RR_ComProt_UNI_AtrmIpBase" {
                                when "not ((./../../Protocol_UNI/RR_ComProt_UNI_Mode != 'Master') or (./../../Protocol_UNI/RR_ComProt_UNI_AtrMethod = 'Table'))";
                                type "inet:ipv4-address";
                            }
                            leaf "RR_ComProt_UNI_AtrmUdpPort" {
                                when "not ((./../../Protocol_UNI/RR_ComProt_UNI_AtrMethod = 'Table') or (./../../Protocol_UNI/RR_ComProt_UNI_DstStdPort != 'MANUAL'))";
                                type "lim_udp_port";
                            }
                            leaf "RR_ComProt_UNI_AtrMethod" {
                                when "not (./../../Protocol_UNI/RR_ComProt_UNI_Mode != 'Master')";
                                type "lbox_com_prot_addr_mode";
                            }
                            leaf "RR_ComProt_UNI_AtrmIpMask" {
                                when "not ((./../../Protocol_UNI/RR_ComProt_UNI_Mode != 'Master') or (./../../Protocol_UNI/RR_ComProt_UNI_AtrMethod = 'Table'))";
                                type "lim_ipv4_mask";
                            }
                            leaf "RR_ComProt_UNI_DstStdPort" {
                                when "not ((./../../Protocol_UNI/RR_ComProt_UNI_Mode != 'Master') or (./../../Protocol_UNI/RR_ComProt_UNI_AtrMethod = 'Table'))";
                                type "lbox_udp_reserved_ports";
                            }
                        }
                        list "RR_S_TABLE_Protocol_UNI_TTable" {
                            when "not ((./../Protocol_UNI/RR_ComProt_UNI_AtrMethod = 'Mask') or (./../Protocol_UNI/RR_ComProt_UNI_Mode = 'Slave'))";
                            key "ID";
                            max-elements "1024";
                            ordered-by "user";
                            leaf "ID" {
                                type "lim_uint_16";
                            }
                            leaf "TTEntry_UNI_Ena" {
                                type "lbox_off_on";
                                default "On";
                            }
                            leaf "TTEntry_UNI_Note" {
                                type "string" {
                                    pattern "[^\"`\\\\$;]{0,42}";
                                }
                                default "";
                            }
                            leaf "TTEntry_UNI_DevAddr_2B" {
                                type "lim_uint_16";
                                must ". <= ../TTEntry_UNI_DevAddrLast_2B" {
                                    error-message "valmsg_it_TTEntry_UNI_DevAddr_2B";
                                }
                                default "1";
                            }
                            leaf "TTEntry_UNI_DevAddrLast_2B" {
                                type "lim_uint_16";
                                must ". >= ../TTEntry_UNI_DevAddr_2B" {
                                    error-message "valmsg_it_TTEntry_UNI_DevAddr_2B";
                                }
                                default "1";
                            }
                            leaf "TTEntry_UNI_IpAddr" {
                                type "inet:ipv4-address";
                                default "0.0.0.0";
                            }
                            leaf "TTEntry_UNI_IpInt" {
                                type "lbox_off_on";
                                default "Off";
                            }
                            leaf "TTEntry_UNI_StdPort" {
                                type "lbox_udp_reserved_ports";
                                default "COM1";
                            }
                            leaf "TTEntry_UNI_ManPort" {
                                when "not (../TTEntry_UNI_StdPort != 'MANUAL')";
                                type "lim_udp_port";
                                default "50000";
                            }
                        }
                    }
                }
                case "c-RDS" {
                    when "deref(./_variant_source_ref) = \"RDS\"";
                    container "RDS" {
                        container "Protocol_RDS" {
                            leaf "RR_ComProt_RDS_AckEna" {
                                type "lbox_off_on";
                            }
                            leaf "RR_ComProt_RDS_Repeats" {
                                when "not (./../../Protocol_RDS/RR_ComProt_RDS_AckEna != 'On')";
                                type "uint8" {
                                    range "0..31";
                                }
                            }
                            leaf "RR_ComProt_RDS_AckTimeout" {
                                when "not (./../../Protocol_RDS/RR_ComProt_RDS_AckEna != 'On')";
                                type "uint16" {
                                    range "0..16383";
                                }
                            }
                            leaf "RR_ComProt_RDS_AtrmIpBase" {
                                when "not (./../../Protocol_RDS/RR_ComProt_RDS_AtrMethod = 'Table')";
                                type "inet:ipv4-address";
                            }
                            leaf "RR_ComProt_RDS_AtrmUdpPort" {
                                when "not ((./../../Protocol_RDS/RR_ComProt_RDS_AtrMethod = 'Table') or (./../../Protocol_RDS/RR_ComProt_RDS_DstStdPort != 'MANUAL'))";
                                type "lim_udp_port";
                            }
                            leaf "RR_ComProt_RDS_AtrMethod" {
                                type "lbox_com_prot_addr_mode";
                            }
                            leaf "RR_ComProt_RDS_AtrmIpMask" {
                                when "not (./../../Protocol_RDS/RR_ComProt_RDS_AtrMethod = 'Table')";
                                type "lim_ipv4_mask";
                            }
                            leaf "RR_ComProt_RDS_DstStdPort" {
                                when "not (./../../Protocol_RDS/RR_ComProt_RDS_AtrMethod = 'Table')";
                                type "lbox_udp_reserved_ports";
                            }
                            leaf "RR_ComProt_RDS_LocRespAddr" {
                                type "lim_uint_8";
                            }
                        }
                        list "RR_S_TABLE_Protocol_RDS_TTable" {
                            when "not (./../Protocol_RDS/RR_ComProt_RDS_AtrMethod = 'Mask')";
                            key "ID";
                            max-elements "1024";
                            ordered-by "user";
                            leaf "ID" {
                                type "lim_uint_16";
                            }
                            leaf "TTEntry_RDS_Ena" {
                                type "lbox_off_on";
                                default "On";
                            }
                            leaf "TTEntry_RDS_Note" {
                                type "string" {
                                    pattern "[^\"`\\\\$;]{0,42}";
                                }
                                default "";
                            }
                            leaf "TTEntry_RDS_DevAddr_1B" {
                                type "lim_uint_8";
                                must ". <= ../TTEntry_RDS_DevAddrLast_1B" {
                                    error-message "valmsg_it_TTEntry_RDS_DevAddr_1B";
                                }
                                default "1";
                            }
                            leaf "TTEntry_RDS_DevAddrLast_1B" {
                                type "lim_uint_8";
                                must ". >= ../TTEntry_RDS_DevAddr_1B" {
                                    error-message "valmsg_it_TTEntry_RDS_DevAddr_1B";
                                }
                                default "1";
                            }
                            leaf "TTEntry_RDS_IpAddr" {
                                type "inet:ipv4-address";
                                default "0.0.0.0";
                            }
                            leaf "TTEntry_RDS_IpInt" {
                                type "lbox_off_on";
                                default "Off";
                            }
                            leaf "TTEntry_RDS_StdPort" {
                                type "lbox_udp_reserved_ports";
                                default "COM1";
                            }
                            leaf "TTEntry_RDS_ManPort" {
                                when "not (../TTEntry_RDS_StdPort != 'MANUAL')";
                                type "lim_udp_port";
                                default "50000";
                            }
                        }
                    }
                }
                case "c-ModbusRTU" {
                    when "deref(./_variant_source_ref) = \"ModbusRTU\"";
                    container "ModbusRTU" {
                        container "Protocol_ModbusRTU" {
                            leaf "RR_ComProt_ModbusRTU_AtrmIpBase" {
                                when "not ((./../../Protocol_ModbusRTU/RR_ComProt_ModbusRTU_AtrMethod = 'Table') or (./../../Protocol_ModbusRTU/RR_ComProt_ModbusRTU_Mode = 'Slave'))";
                                type "inet:ipv4-address";
                            }
                            leaf "RR_ComProt_ModbusRTU_AtrmUdpPort" {
                                when "not ((./../../Protocol_ModbusRTU/RR_ComProt_ModbusRTU_AtrMethod = 'Table') or (./../../Protocol_ModbusRTU/RR_ComProt_ModbusRTU_DstStdPort != 'MANUAL'))";
                                type "lim_udp_port";
                            }
                            leaf "RR_ComProt_ModbusRTU_Mode" {
                                type "lbox_com_prot_mode";
                            }
                            leaf "RR_ComProt_ModbusRTU_Bcast" {
                                when "not (/config_data/device/DeviceHw/RR_DynHw_Primary_Radio != 'On')";
                                type "lbox_off_on";
                            }
                            leaf "RR_ComProt_ModbusRTU_AtrMethod" {
                                when "not (./../../Protocol_ModbusRTU/RR_ComProt_ModbusRTU_Mode = 'Slave')";
                                type "lbox_com_prot_addr_mode";
                            }
                            leaf "RR_ComProt_ModbusRTU_AtrmIpMask" {
                                when "not ((./../../Protocol_ModbusRTU/RR_ComProt_ModbusRTU_Mode = 'Slave') or (./../../Protocol_ModbusRTU/RR_ComProt_ModbusRTU_AtrMethod = 'Table'))";
                                type "lim_ipv4_mask";
                            }
                            leaf "RR_ComProt_ModbusRTU_DstStdPort" {
                                when "not (((./../../Protocol_ModbusRTU/RR_ComProt_ModbusRTU_Mode = 'Master') and (./../../Protocol_ModbusRTU/RR_ComProt_ModbusRTU_AtrMethod = 'Table')) or ((./../../Protocol_ModbusRTU/RR_ComProt_ModbusRTU_Mode = 'Slave') and (./../../Protocol_ModbusRTU/RR_ComProt_ModbusRTU_SlaveDst = 'LASTRCV')))";
                                type "lbox_udp_reserved_ports";
                            }
                            leaf "RR_ComProt_ModbusRTU_SlaveDst" {
                                when "not (./../../Protocol_ModbusRTU/RR_ComProt_ModbusRTU_Mode != 'Slave')";
                                type "lbox_com_prot_slave_dst";
                            }
                            leaf "RR_ComProt_ModbusRTU_BcastAddress" {
                                when "not ((/config_data/device/DeviceHw/RR_DynHw_Primary_Radio != 'On') or (./../../Protocol_ModbusRTU/RR_ComProt_ModbusRTU_Mode != 'Master') or (./../../Protocol_ModbusRTU/RR_ComProt_ModbusRTU_Bcast != 'On'))";
                                type "lim_uint_8";
                            }
                            leaf "RR_ComProt_ModbusRTU_ResponseTimeout" {
                                when "not (./../../Protocol_ModbusRTU/RR_ComProt_ModbusRTU_Mode != 'Slave')";
                                type "uint16" {
                                    range "0..8190";
                                }
                            }
                            leaf "RR_ComProt_ModbusRTU_SlaveTargetIp" {
                                when "not ((./../../Protocol_ModbusRTU/RR_ComProt_ModbusRTU_Mode = 'Master') or ((./../../Protocol_ModbusRTU/RR_ComProt_ModbusRTU_Mode = 'Slave') and (./../../Protocol_ModbusRTU/RR_ComProt_ModbusRTU_SlaveDst = 'LASTRCV')))";
                                type "inet:ipv4-address";
                            }
                        }
                        list "RR_S_TABLE_Protocol_ModbusRTU_TTable" {
                            when "not ((./../Protocol_ModbusRTU/RR_ComProt_ModbusRTU_AtrMethod = 'Mask') or (./../Protocol_ModbusRTU/RR_ComProt_ModbusRTU_Mode = 'Slave'))";
                            key "ID";
                            max-elements "1024";
                            ordered-by "user";
                            leaf "ID" {
                                type "lim_uint_16";
                            }
                            leaf "TTEntry_ModbusRTU_Ena" {
                                type "lbox_off_on";
                                default "On";
                            }
                            leaf "TTEntry_ModbusRTU_Note" {
                                type "string" {
                                    pattern "[^\"`\\\\$;]{0,42}";
                                }
                                default "";
                            }
                            leaf "TTEntry_ModbusRTU_DevAddr_1B" {
                                type "lim_uint_8";
                                must ". <= ../TTEntry_ModbusRTU_DevAddrLast_1B" {
                                    error-message "valmsg_it_TTEntry_ModbusRTU_DevAddr_1B";
                                }
                                default "1";
                            }
                            leaf "TTEntry_ModbusRTU_DevAddrLast_1B" {
                                type "lim_uint_8";
                                must ". >= ../TTEntry_ModbusRTU_DevAddr_1B" {
                                    error-message "valmsg_it_TTEntry_ModbusRTU_DevAddr_1B";
                                }
                                default "1";
                            }
                            leaf "TTEntry_ModbusRTU_IpAddr" {
                                type "inet:ipv4-address";
                                default "0.0.0.0";
                            }
                            leaf "TTEntry_ModbusRTU_IpInt" {
                                type "lbox_off_on";
                                default "Off";
                            }
                            leaf "TTEntry_ModbusRTU_StdPort" {
                                type "lbox_udp_reserved_ports";
                                default "COM1";
                            }
                            leaf "TTEntry_ModbusRTU_ManPort" {
                                when "not (../TTEntry_ModbusRTU_StdPort != 'MANUAL')";
                                type "lim_udp_port";
                                default "50000";
                            }
                        }
                    }
                }
                case "c-PR2000" {
                    when "deref(./_variant_source_ref) = \"PR2000\"";
                    container "PR2000" {
                        container "Protocol_PR2000" {
                            leaf "RR_ComProt_PR2000_AtrmIpBase" {
                                when "not ((./../../Protocol_PR2000/RR_ComProt_PR2000_AtrMethod = 'Table') or (./../../Protocol_PR2000/RR_ComProt_PR2000_Mode = 'Slave'))";
                                type "inet:ipv4-address";
                            }
                            leaf "RR_ComProt_PR2000_AtrmUdpPort" {
                                when "not ((./../../Protocol_PR2000/RR_ComProt_PR2000_AtrMethod = 'Table') or (./../../Protocol_PR2000/RR_ComProt_PR2000_DstStdPort != 'MANUAL'))";
                                type "lim_udp_port";
                            }
                            leaf "RR_ComProt_PR2000_Sync" {
                                type "lim_uint_16";
                            }
                            leaf "RR_ComProt_PR2000_Mode" {
                                type "lbox_com_prot_mode";
                            }
                            leaf "RR_ComProt_PR2000_Bcast" {
                                when "not (/config_data/device/DeviceHw/RR_DynHw_Primary_Radio != 'On')";
                                type "lbox_off_on";
                            }
                            leaf "RR_ComProt_PR2000_AtrMethod" {
                                when "not (./../../Protocol_PR2000/RR_ComProt_PR2000_Mode = 'Slave')";
                                type "lbox_com_prot_addr_mode";
                            }
                            leaf "RR_ComProt_PR2000_AtrmIpMask" {
                                when "not ((./../../Protocol_PR2000/RR_ComProt_PR2000_Mode = 'Slave') or (./../../Protocol_PR2000/RR_ComProt_PR2000_AtrMethod = 'Table'))";
                                type "lim_ipv4_mask";
                            }
                            leaf "RR_ComProt_PR2000_DstStdPort" {
                                when "not (((./../../Protocol_PR2000/RR_ComProt_PR2000_Mode = 'Master') and (./../../Protocol_PR2000/RR_ComProt_PR2000_AtrMethod = 'Table')) or ((./../../Protocol_PR2000/RR_ComProt_PR2000_Mode = 'Slave') and (./../../Protocol_PR2000/RR_ComProt_PR2000_SlaveDst = 'LASTRCV')))";
                                type "lbox_udp_reserved_ports";
                            }
                            leaf "RR_ComProt_PR2000_SlaveDst" {
                                when "not (./../../Protocol_PR2000/RR_ComProt_PR2000_Mode != 'Slave')";
                                type "lbox_com_prot_slave_dst";
                            }
                            leaf "RR_ComProt_PR2000_SlaveTargetIp" {
                                when "not ((./../../Protocol_PR2000/RR_ComProt_PR2000_Mode = 'Master') or ((./../../Protocol_PR2000/RR_ComProt_PR2000_Mode = 'Slave') and (./../../Protocol_PR2000/RR_ComProt_PR2000_SlaveDst = 'LASTRCV')))";
                                type "inet:ipv4-address";
                            }
                        }
                        list "RR_S_TABLE_Protocol_PR2000_TTable" {
                            when "not ((./../Protocol_PR2000/RR_ComProt_PR2000_AtrMethod = 'Mask') or (./../Protocol_PR2000/RR_ComProt_PR2000_Mode = 'Slave'))";
                            key "ID";
                            max-elements "1024";
                            ordered-by "user";
                            leaf "ID" {
                                type "lim_uint_16";
                            }
                            leaf "TTEntry_PR2000_Ena" {
                                type "lbox_off_on";
                                default "On";
                            }
                            leaf "TTEntry_PR2000_Note" {
                                type "string" {
                                    pattern "[^\"`\\\\$;]{0,42}";
                                }
                                default "";
                            }
                            leaf "TTEntry_PR2000_DevAddr_1B" {
                                type "lim_uint_8";
                                must ". <= ../TTEntry_PR2000_DevAddrLast_1B" {
                                    error-message "valmsg_it_TTEntry_PR2000_DevAddr_1B";
                                }
                                default "1";
                            }
                            leaf "TTEntry_PR2000_DevAddrLast_1B" {
                                type "lim_uint_8";
                                must ". >= ../TTEntry_PR2000_DevAddr_1B" {
                                    error-message "valmsg_it_TTEntry_PR2000_DevAddr_1B";
                                }
                                default "1";
                            }
                            leaf "TTEntry_PR2000_IpAddr" {
                                type "inet:ipv4-address";
                                default "0.0.0.0";
                            }
                            leaf "TTEntry_PR2000_IpInt" {
                                type "lbox_off_on";
                                default "Off";
                            }
                            leaf "TTEntry_PR2000_StdPort" {
                                type "lbox_udp_reserved_ports";
                                default "COM1";
                            }
                            leaf "TTEntry_PR2000_ManPort" {
                                when "not (../TTEntry_PR2000_StdPort != 'MANUAL')";
                                type "lim_udp_port";
                                default "50000";
                            }
                        }
                    }
                }
                case "c-S3964R" {
                    when "deref(./_variant_source_ref) = \"S3964R\"";
                    container "S3964R" {
                        container "Protocol_S3964R" {
                            leaf "RR_ComProt_S3964R_AtrmIpBase" {
                                when "not ((./../../Protocol_S3964R/RR_ComProt_S3964R_AtrMethod = 'Table') or (./../../Protocol_S3964R/RR_ComProt_S3964R_Mode = 'Slave'))";
                                type "inet:ipv4-address";
                            }
                            leaf "RR_ComProt_S3964R_AtrmUdpPort" {
                                when "not ((./../../Protocol_S3964R/RR_ComProt_S3964R_AtrMethod = 'Table') or (./../../Protocol_S3964R/RR_ComProt_S3964R_DstStdPort != 'MANUAL'))";
                                type "lim_udp_port";
                            }
                            leaf "RR_ComProt_S3964R_Mode" {
                                type "lbox_com_prot_mode";
                            }
                            leaf "RR_ComProt_S3964R_Bcast" {
                                when "not (/config_data/device/DeviceHw/RR_DynHw_Primary_Radio != 'On')";
                                type "lbox_off_on";
                            }
                            leaf "RR_ComProt_S3964R_AtrMethod" {
                                when "not (./../../Protocol_S3964R/RR_ComProt_S3964R_Mode = 'Slave')";
                                type "lbox_com_prot_addr_mode";
                            }
                            leaf "RR_ComProt_S3964R_AtrmIpMask" {
                                when "not ((./../../Protocol_S3964R/RR_ComProt_S3964R_Mode = 'Slave') or (./../../Protocol_S3964R/RR_ComProt_S3964R_AtrMethod = 'Table'))";
                                type "lim_ipv4_mask";
                            }
                            leaf "RR_ComProt_S3964R_DstStdPort" {
                                when "not (((./../../Protocol_S3964R/RR_ComProt_S3964R_Mode = 'Master') and (./../../Protocol_S3964R/RR_ComProt_S3964R_AtrMethod = 'Table')) or ((./../../Protocol_S3964R/RR_ComProt_S3964R_Mode = 'Slave') and (./../../Protocol_S3964R/RR_ComProt_S3964R_SlaveDst = 'LASTRCV')))";
                                type "lbox_udp_reserved_ports";
                            }
                            leaf "RR_ComProt_S3964R_SlaveDst" {
                                when "not (./../../Protocol_S3964R/RR_ComProt_S3964R_Mode != 'Slave')";
                                type "lbox_com_prot_slave_dst";
                            }
                            leaf "RR_ComProt_S3964R_AddrPos" {
                                when "not (./../../Protocol_S3964R/RR_ComProt_S3964R_Mode != 'Master')";
                                type "lim_uint_8_1toFF";
                            }
                            leaf "RR_ComProt_S3964R_BcastAddress" {
                                when "not ((/config_data/device/DeviceHw/RR_DynHw_Primary_Radio != 'On') or (./../../Protocol_S3964R/RR_ComProt_S3964R_Mode != 'Master') or (./../../Protocol_S3964R/RR_ComProt_S3964R_Bcast != 'On'))";
                                type "lim_uint_16";
                            }
                            leaf "RR_ComProt_S3964R_DLETimeout" {
                                type "uint16" {
                                    range "300..8190";
                                }
                            }
                            leaf "RR_ComProt_S3964R_Repeats" {
                                type "uint8" {
                                    range "0..7";
                                }
                            }
                            leaf "RR_ComProt_S3964R_AddrMode" {
                                when "not (./../../Protocol_S3964R/RR_ComProt_S3964R_Mode != 'Master')";
                                type "enumeration" {
                                    enum "bin_1B" {
                                        value "0";
                                    }
                                    enum "bin_2B_LSB" {
                                        value "1";
                                    }
                                    enum "bin_2B_MSB" {
                                        value "2";
                                    }
                                }
                            }
                            leaf "RR_ComProt_S3964R_BCC" {
                                type "lbox_off_on";
                            }
                            leaf "RR_ComProt_S3964R_Priority" {
                                type "enumeration" {
                                    enum "Low" {
                                        value "0";
                                    }
                                    enum "High" {
                                        value "1";
                                    }
                                }
                            }
                            leaf "RR_ComProt_S3964R_SlaveTargetIp" {
                                when "not ((./../../Protocol_S3964R/RR_ComProt_S3964R_Mode = 'Master') or ((./../../Protocol_S3964R/RR_ComProt_S3964R_Mode = 'Slave') and (./../../Protocol_S3964R/RR_ComProt_S3964R_SlaveDst = 'LASTRCV')))";
                                type "inet:ipv4-address";
                            }
                        }
                        list "RR_S_TABLE_Protocol_S3964R_TTable" {
                            when "not ((./../Protocol_S3964R/RR_ComProt_S3964R_AtrMethod = 'Mask') or (./../Protocol_S3964R/RR_ComProt_S3964R_Mode = 'Slave'))";
                            key "ID";
                            max-elements "1024";
                            ordered-by "user";
                            leaf "ID" {
                                type "lim_uint_16";
                            }
                            leaf "TTEntry_S3964R_Ena" {
                                type "lbox_off_on";
                                default "On";
                            }
                            leaf "TTEntry_S3964R_Note" {
                                type "string" {
                                    pattern "[^\"`\\\\$;]{0,42}";
                                }
                                default "";
                            }
                            leaf "TTEntry_S3964R_DevAddr_2B" {
                                type "lim_uint_16";
                                must ". <= ../TTEntry_S3964R_DevAddrLast_2B" {
                                    error-message "valmsg_it_TTEntry_S3964R_DevAddr_2B";
                                }
                                default "1";
                            }
                            leaf "TTEntry_S3964R_DevAddrLast_2B" {
                                type "lim_uint_16";
                                must ". >= ../TTEntry_S3964R_DevAddr_2B" {
                                    error-message "valmsg_it_TTEntry_S3964R_DevAddr_2B";
                                }
                                default "1";
                            }
                            leaf "TTEntry_S3964R_IpAddr" {
                                type "inet:ipv4-address";
                                default "0.0.0.0";
                            }
                            leaf "TTEntry_S3964R_IpInt" {
                                type "lbox_off_on";
                                default "Off";
                            }
                            leaf "TTEntry_S3964R_StdPort" {
                                type "lbox_udp_reserved_ports";
                                default "COM1";
                            }
                            leaf "TTEntry_S3964R_ManPort" {
                                when "not (../TTEntry_S3964R_StdPort != 'MANUAL')";
                                type "lim_udp_port";
                                default "50000";
                            }
                        }
                    }
                }
                case "c-SAIA_S-BUS" {
                    when "deref(./_variant_source_ref) = \"SAIA_S-BUS\"";
                    container "SAIA_S-BUS" {
                        container "Protocol_SAIA_SBUS" {
                            leaf "RR_ComProt_SAIA_SBUS_AtrmIpBase" {
                                when "not ((./../../Protocol_SAIA_SBUS/RR_ComProt_SAIA_SBUS_AtrMethod = 'Table') or (./../../Protocol_SAIA_SBUS/RR_ComProt_SAIA_SBUS_Mode = 'Slave'))";
                                type "inet:ipv4-address";
                            }
                            leaf "RR_ComProt_SAIA_SBUS_AtrmUdpPort" {
                                when "not ((./../../Protocol_SAIA_SBUS/RR_ComProt_SAIA_SBUS_AtrMethod = 'Table') or (./../../Protocol_SAIA_SBUS/RR_ComProt_SAIA_SBUS_DstStdPort != 'MANUAL'))";
                                type "lim_udp_port";
                            }
                            leaf "RR_ComProt_SAIA_SBUS_Mode" {
                                type "lbox_com_prot_mode_plus";
                            }
                            leaf "RR_ComProt_SAIA_SBUS_Bcast" {
                                when "not (/config_data/device/DeviceHw/RR_DynHw_Primary_Radio != 'On')";
                                type "lbox_off_on";
                            }
                            leaf "RR_ComProt_SAIA_SBUS_AtrMethod" {
                                when "not (./../../Protocol_SAIA_SBUS/RR_ComProt_SAIA_SBUS_Mode = 'Slave')";
                                type "lbox_com_prot_addr_mode";
                            }
                            leaf "RR_ComProt_SAIA_SBUS_AtrmIpMask" {
                                when "not ((./../../Protocol_SAIA_SBUS/RR_ComProt_SAIA_SBUS_Mode = 'Slave') or (./../../Protocol_SAIA_SBUS/RR_ComProt_SAIA_SBUS_AtrMethod = 'Table'))";
                                type "lim_ipv4_mask";
                            }
                            leaf "RR_ComProt_SAIA_SBUS_DstStdPort" {
                                when "not (((./../../Protocol_SAIA_SBUS/RR_ComProt_SAIA_SBUS_Mode = 'Master') and (./../../Protocol_SAIA_SBUS/RR_ComProt_SAIA_SBUS_AtrMethod = 'Table')) or ((./../../Protocol_SAIA_SBUS/RR_ComProt_SAIA_SBUS_Mode = 'SlavePlus') and (./../../Protocol_SAIA_SBUS/RR_ComProt_SAIA_SBUS_AtrMethod = 'Table')) or (./../../Protocol_SAIA_SBUS/RR_ComProt_SAIA_SBUS_Mode = 'Slave'))";
                                type "lbox_udp_reserved_ports";
                            }
                            leaf "RR_ComProt_SAIA_SBUS_SlaveDst" {
                                when "not (./../../Protocol_SAIA_SBUS/RR_ComProt_SAIA_SBUS_Mode = 'Master')";
                                type "lbox_com_prot_slave_dst";
                            }
                            leaf "RR_ComProt_SAIA_SBUS_SlaveTargetIp" {
                                when "not ((./../../Protocol_SAIA_SBUS/RR_ComProt_SAIA_SBUS_Mode = 'Master') or ((./../../Protocol_SAIA_SBUS/RR_ComProt_SAIA_SBUS_Mode = 'SlavePlus') and (./../../Protocol_SAIA_SBUS/RR_ComProt_SAIA_SBUS_SlaveDst = 'LASTRCV')) or ((./../../Protocol_SAIA_SBUS/RR_ComProt_SAIA_SBUS_Mode = 'Slave') and (./../../Protocol_SAIA_SBUS/RR_ComProt_SAIA_SBUS_SlaveDst = 'LASTRCV')))";
                                type "inet:ipv4-address";
                            }
                            leaf "RR_ComProt_SAIA_SBUS_RepeatTimeout" {
                                when "not (./../../Protocol_SAIA_SBUS/RR_ComProt_SAIA_SBUS_Mode = 'Master')";
                                type "uint16" {
                                    range "0..16383";
                                }
                            }
                            leaf "RR_ComProt_SAIA_SBUS_ResponseTimeoutCongestion" {
                                when "not (./../../Protocol_SAIA_SBUS/RR_ComProt_SAIA_SBUS_Mode != 'Master')";
                                type "lim_uint_16";
                            }
                            leaf "RR_ComProt_SAIA_SBUS_Repeats" {
                                when "not (./../../Protocol_SAIA_SBUS/RR_ComProt_SAIA_SBUS_Mode = 'Master')";
                                type "uint8" {
                                    range "0..7";
                                }
                            }
                            leaf "RR_ComProt_SAIA_SBUS_DstStdPortSlave" {
                                when "not ((./../../Protocol_SAIA_SBUS/RR_ComProt_SAIA_SBUS_Mode = 'Master') or ((./../../Protocol_SAIA_SBUS/RR_ComProt_SAIA_SBUS_Mode = 'Slave') and (./../../Protocol_SAIA_SBUS/RR_ComProt_SAIA_SBUS_SlaveDst = 'LASTRCV')) or ((./../../Protocol_SAIA_SBUS/RR_ComProt_SAIA_SBUS_Mode = 'SlavePlus') and (./../../Protocol_SAIA_SBUS/RR_ComProt_SAIA_SBUS_SlaveDst = 'LASTRCV')))";
                                type "lbox_udp_reserved_ports";
                            }
                            leaf "RR_ComProt_SAIA_SBUS_AtrmUdpPortSlave" {
                                when "not (./../../Protocol_SAIA_SBUS/RR_ComProt_SAIA_SBUS_DstStdPortSlave != 'MANUAL')";
                                type "lim_udp_port";
                            }
                        }
                        container "Protocol_SAIA_SBUS_BREAK" {
                            leaf "RR_ComProt_SAIA_SBUS_DataMode" {
                                type "lbox_com_prot_saia_sbus_mode";
                            }
                            leaf "RR_ComProt_SAIA_SBUS_BreakDuration" {
                                when "not ((./../../Protocol_SAIA_SBUS/RR_ComProt_SAIA_SBUS_Mode = 'Master') or (./../../Protocol_SAIA_SBUS_BREAK/RR_ComProt_SAIA_SBUS_DataMode = 'Data'))";
                                type "uint8" {
                                    range "0..128";
                                }
                            }
                            leaf "RR_ComProt_SAIA_SBUS_BreakValidityTime" {
                                when "not ((./../../Protocol_SAIA_SBUS/RR_ComProt_SAIA_SBUS_Mode = 'Slave') or (./../../Protocol_SAIA_SBUS_BREAK/RR_ComProt_SAIA_SBUS_DataMode = 'Data'))";
                                type "uint16" {
                                    range "0..5000";
                                }
                            }
                        }
                        list "RR_S_TABLE_Protocol_SAIA_SBUS_TTable" {
                            when "not ((./../Protocol_SAIA_SBUS/RR_ComProt_SAIA_SBUS_AtrMethod = 'Mask') or (./../Protocol_SAIA_SBUS/RR_ComProt_SAIA_SBUS_Mode = 'Slave'))";
                            key "ID";
                            max-elements "1024";
                            ordered-by "user";
                            leaf "ID" {
                                type "lim_uint_16";
                            }
                            leaf "TTEntry_SAIA_SBUS_Ena" {
                                type "lbox_off_on";
                                default "On";
                            }
                            leaf "TTEntry_SAIA_SBUS_Note" {
                                type "string" {
                                    pattern "[^\"`\\\\$;]{0,42}";
                                }
                                default "";
                            }
                            leaf "TTEntry_SAIA_SBUS_DevAddr_1B" {
                                type "lim_uint_8";
                                must ". <= ../TTEntry_SAIA_SBUS_DevAddrLast_1B" {
                                    error-message "valmsg_it_TTEntry_SAIA_SBUS_DevAddr_1B";
                                }
                                default "1";
                            }
                            leaf "TTEntry_SAIA_SBUS_DevAddrLast_1B" {
                                type "lim_uint_8";
                                must ". >= ../TTEntry_SAIA_SBUS_DevAddr_1B" {
                                    error-message "valmsg_it_TTEntry_SAIA_SBUS_DevAddr_1B";
                                }
                                default "1";
                            }
                            leaf "TTEntry_SAIA_SBUS_IpAddr" {
                                type "inet:ipv4-address";
                                default "0.0.0.0";
                            }
                            leaf "TTEntry_SAIA_SBUS_IpInt" {
                                type "lbox_off_on";
                                default "Off";
                            }
                            leaf "TTEntry_SAIA_SBUS_StdPort" {
                                type "lbox_udp_reserved_ports";
                                default "COM1";
                            }
                            leaf "TTEntry_SAIA_SBUS_ManPort" {
                                when "not (../TTEntry_SAIA_SBUS_StdPort != 'MANUAL')";
                                type "lim_udp_port";
                                default "50000";
                            }
                        }
                    }
                }
                case "c-Mars-A" {
                    when "deref(./_variant_source_ref) = \"Mars-A\"";
                    container "Mars-A" {
                        container "Protocol_MarsA" {
                            leaf "RR_ComProt_MarsA_AtrmIpBase" {
                                when "not (./../../Protocol_MarsA/RR_ComProt_MarsA_AtrMethod = 'Table')";
                                type "inet:ipv4-address";
                            }
                            leaf "RR_ComProt_MarsA_AtrmUdpPort" {
                                when "not ((./../../Protocol_MarsA/RR_ComProt_MarsA_AtrMethod = 'Table') or (./../../Protocol_MarsA/RR_ComProt_MarsA_DstStdPort != 'MANUAL'))";
                                type "lim_udp_port";
                            }
                            leaf "RR_ComProt_MarsA_Repeats" {
                                type "uint8" {
                                    range "0..31";
                                }
                            }
                            leaf "RR_ComProt_MarsA_Bcast" {
                                when "not (/config_data/device/DeviceHw/RR_DynHw_Primary_Radio != 'On')";
                                type "lbox_off_on";
                            }
                            leaf "RR_ComProt_MarsA_Crc" {
                                type "lbox_off_on";
                            }
                            leaf "RR_ComProt_MarsA_AtrMethod" {
                                type "lbox_com_prot_addr_mode";
                            }
                            leaf "RR_ComProt_MarsA_AtrmIpMask" {
                                when "not (./../../Protocol_MarsA/RR_ComProt_MarsA_AtrMethod = 'Table')";
                                type "lim_ipv4_mask";
                            }
                            leaf "RR_ComProt_MarsA_SecurityBit" {
                                type "lbox_off_on";
                            }
                            leaf "RR_ComProt_MarsA_DstStdPort" {
                                when "not (./../../Protocol_MarsA/RR_ComProt_MarsA_AtrMethod = 'Table')";
                                type "lbox_udp_reserved_ports";
                            }
                            leaf "RR_ComProt_MarsA_RepeatTimeout" {
                                type "uint16" {
                                    range "0..16383";
                                }
                            }
                        }
                        list "RR_S_TABLE_Protocol_MarsA_TTable" {
                            when "not (./../Protocol_MarsA/RR_ComProt_MarsA_AtrMethod = 'Mask')";
                            key "ID";
                            max-elements "1024";
                            ordered-by "user";
                            leaf "ID" {
                                type "lim_uint_16";
                            }
                            leaf "TTEntry_MarsA_Ena" {
                                type "lbox_off_on";
                                default "On";
                            }
                            leaf "TTEntry_MarsA_Note" {
                                type "string" {
                                    pattern "[^\"`\\\\$;]{0,42}";
                                }
                                default "";
                            }
                            leaf "TTEntry_MarsA_DevAddr_4B" {
                                type "lim_uint_32";
                                must ". <= ../TTEntry_MarsA_DevAddrLast_4B" {
                                    error-message "valmsg_it_TTEntry_MarsA_DevAddr_4B";
                                }
                                default "1";
                            }
                            leaf "TTEntry_MarsA_DevAddrLast_4B" {
                                type "lim_uint_32";
                                must ". >= ../TTEntry_MarsA_DevAddr_4B" {
                                    error-message "valmsg_it_TTEntry_MarsA_DevAddr_4B";
                                }
                                default "1";
                            }
                            leaf "TTEntry_MarsA_IpAddr" {
                                type "inet:ipv4-address";
                                default "0.0.0.0";
                            }
                            leaf "TTEntry_MarsA_IpInt" {
                                type "lbox_off_on";
                                default "Off";
                            }
                            leaf "TTEntry_MarsA_StdPort" {
                                type "lbox_udp_reserved_ports";
                                default "COM1";
                            }
                            leaf "TTEntry_MarsA_ManPort" {
                                when "not (../TTEntry_MarsA_StdPort != 'MANUAL')";
                                type "lim_udp_port";
                                default "50000";
                            }
                        }
                    }
                }
                case "c-COMLI" {
                    when "deref(./_variant_source_ref) = \"COMLI\"";
                    container "COMLI" {
                        container "Protocol_COMLI" {
                            leaf "RR_ComProt_COMLI_AtrmIpBase" {
                                when "not ((./../../Protocol_COMLI/RR_ComProt_COMLI_AtrMethod = 'Table') or (./../../Protocol_COMLI/RR_ComProt_COMLI_Mode = 'Slave'))";
                                type "inet:ipv4-address";
                            }
                            leaf "RR_ComProt_COMLI_AtrmUdpPort" {
                                when "not ((./../../Protocol_COMLI/RR_ComProt_COMLI_AtrMethod = 'Table') or (./../../Protocol_COMLI/RR_ComProt_COMLI_DstStdPort != 'MANUAL'))";
                                type "lim_udp_port";
                            }
                            leaf "RR_ComProt_COMLI_Mode" {
                                type "lbox_com_prot_mode";
                            }
                            leaf "RR_ComProt_COMLI_AtrMethod" {
                                when "not (./../../Protocol_COMLI/RR_ComProt_COMLI_Mode = 'Slave')";
                                type "lbox_com_prot_addr_mode";
                            }
                            leaf "RR_ComProt_COMLI_AtrmIpMask" {
                                when "not ((./../../Protocol_COMLI/RR_ComProt_COMLI_Mode = 'Slave') or (./../../Protocol_COMLI/RR_ComProt_COMLI_AtrMethod = 'Table'))";
                                type "lim_ipv4_mask";
                            }
                            leaf "RR_ComProt_COMLI_DstStdPort" {
                                when "not (((./../../Protocol_COMLI/RR_ComProt_COMLI_Mode = 'Master') and (./../../Protocol_COMLI/RR_ComProt_COMLI_AtrMethod = 'Table')) or ((./../../Protocol_COMLI/RR_ComProt_COMLI_Mode = 'Slave') and (./../../Protocol_COMLI/RR_ComProt_COMLI_SlaveDst = 'LASTRCV')))";
                                type "lbox_udp_reserved_ports";
                            }
                            leaf "RR_ComProt_COMLI_SlaveDst" {
                                when "not (./../../Protocol_COMLI/RR_ComProt_COMLI_Mode != 'Slave')";
                                type "lbox_com_prot_slave_dst";
                            }
                            leaf "RR_ComProt_COMLI_ResponseTimeout" {
                                when "not (./../../Protocol_COMLI/RR_ComProt_COMLI_Mode != 'Slave')";
                                type "uint16" {
                                    range "0..16383";
                                }
                            }
                            leaf "RR_ComProt_COMLI_CongestionTimeout" {
                                when "not (./../../Protocol_COMLI/RR_ComProt_COMLI_Mode != 'Master')";
                                type "uint16" {
                                    range "0..65535";
                                }
                            }
                            leaf "RR_ComProt_COMLI_SlaveTargetIp" {
                                when "not ((./../../Protocol_COMLI/RR_ComProt_COMLI_Mode = 'Master') or ((./../../Protocol_COMLI/RR_ComProt_COMLI_Mode = 'Slave') and (./../../Protocol_COMLI/RR_ComProt_COMLI_SlaveDst = 'LASTRCV')))";
                                type "inet:ipv4-address";
                            }
                        }
                        list "RR_S_TABLE_Protocol_COMLI_TTable" {
                            when "not (./../Protocol_COMLI/RR_ComProt_COMLI_AtrMethod = 'Mask')";
                            key "ID";
                            max-elements "1024";
                            ordered-by "user";
                            leaf "ID" {
                                type "lim_uint_16";
                            }
                            leaf "TTEntry_COMLI_Ena" {
                                type "lbox_off_on";
                                default "On";
                            }
                            leaf "TTEntry_COMLI_Note" {
                                type "string" {
                                    pattern "[^\"`\\\\$;]{0,42}";
                                }
                                default "";
                            }
                            leaf "TTEntry_COMLI_DevAddr_1B" {
                                type "lim_uint_8";
                                must ". <= ../TTEntry_COMLI_DevAddrLast_1B" {
                                    error-message "valmsg_it_TTEntry_COMLI_DevAddr_1B";
                                }
                                default "1";
                            }
                            leaf "TTEntry_COMLI_DevAddrLast_1B" {
                                type "lim_uint_8";
                                must ". >= ../TTEntry_COMLI_DevAddr_1B" {
                                    error-message "valmsg_it_TTEntry_COMLI_DevAddr_1B";
                                }
                                default "1";
                            }
                            leaf "TTEntry_COMLI_IpAddr" {
                                type "inet:ipv4-address";
                                default "0.0.0.0";
                            }
                            leaf "TTEntry_COMLI_IpInt" {
                                type "lbox_off_on";
                                default "Off";
                            }
                            leaf "TTEntry_COMLI_StdPort" {
                                type "lbox_udp_reserved_ports";
                                default "COM1";
                            }
                            leaf "TTEntry_COMLI_ManPort" {
                                when "not (../TTEntry_COMLI_StdPort != 'MANUAL')";
                                type "lim_udp_port";
                                default "50000";
                            }
                        }
                    }
                }
                case "c-PPP" {
                    when "deref(./_variant_source_ref) = \"PPP\"";
                    container "PPP" {
                        container "Protocol_PPP" {
                            leaf "RR_ComProt_PPP_LocalNetAddr" {
                                type "inet:ipv4-address";
                            }
                            leaf "RR_ComProt_PPP_RemoteNetAddr" {
                                type "inet:ipv4-address";
                            }
                            leaf "RR_ComProt_PPP_NetMask" {
                                type "lim_ipv4_mask0";
                            }
                            leaf "RR_ComProt_PPP_LocalAuthMode" {
                                type "lbox_com_prot_auth_mode";
                            }
                            leaf "RR_ComProt_PPP_LocalAuthUsername" {
                                when "not (./../../Protocol_PPP/RR_ComProt_PPP_LocalAuthMode = 'LB_com_prot_auth_mode_None')";
                                type "string" {
                                    pattern "[ !#%-:<-\\[\\]-_a-~]{0,50}";
                                }
                            }
                            leaf "RR_ComProt_PPP_LocalAuthPassword" {
                                when "not (./../../Protocol_PPP/RR_ComProt_PPP_LocalAuthMode = 'LB_com_prot_auth_mode_None')";
                                type "string" {
                                    pattern "[ !#%-:<-\\[\\]-_a-~]{0,50}";
                                }
                            }
                            leaf "RR_ComProt_PPP_Username" {
                                type "string" {
                                    pattern "[ !#%-:<-\\[\\]-_a-~]{0,50}";
                                }
                            }
                            leaf "RR_ComProt_PPP_Password" {
                                type "string" {
                                    pattern "[ !#%-:<-\\[\\]-_a-~]{0,50}";
                                }
                            }
                            leaf "RR_ComProt_PPP_AsyncMap" {
                                type "lim_uint_16";
                            }
                            leaf "RR_ComProt_PPP_LcpKeepFailureCnt" {
                                type "lim_uint_8";
                            }
                            leaf "RR_ComProt_PPP_LcpKeepInterval" {
                                when "not (./../../Protocol_PPP/RR_ComProt_PPP_LcpKeepFailureCnt = '0')";
                                type "lim_uint_16_1toFF";
                            }
                            leaf "RR_ComProt_PPP_IdleTimeout" {
                                type "lim_uint_16";
                            }
                            leaf "RR_ComProt_PPP_MngEn" {
                                type "lbox_off_on";
                            }
                            leaf "RR_ComProt_PPP_ModemCtrlLinesEn" {
                                type "lbox_off_on";
                            }
                            leaf "RR_ComProt_PPP_CtrlMsgLogEn" {
                                type "lbox_off_on";
                            }
                            leaf "RR_ComProt_PPP_ComprNegMode" {
                                type "lbox_auto_manual";
                            }
                            leaf "RR_ComProt_PPP_ComprAddrFieldEn" {
                                when "not (./../../Protocol_PPP/RR_ComProt_PPP_ComprNegMode != 'LB_auto_manual_Manual')";
                                type "lbox_off_on";
                            }
                            leaf "RR_ComProt_PPP_ComprProtFieldEn" {
                                when "not (./../../Protocol_PPP/RR_ComProt_PPP_ComprNegMode != 'LB_auto_manual_Manual')";
                                type "lbox_off_on";
                            }
                            leaf "RR_ComProt_PPP_ComprVjHeaderSlots" {
                                when "not (./../../Protocol_PPP/RR_ComProt_PPP_ComprNegMode != 'LB_auto_manual_Manual')";
                                type "uint8";
                                must ". = '0' or (. >= 2 and . <= 16)" {
                                    error-message "valmsg_it_PPP_ComprVjHeaderSlots";
                                }
                            }
                            leaf "RR_ComProt_PPP_ComprCtrlProtEn" {
                                when "not (./../../Protocol_PPP/RR_ComProt_PPP_ComprNegMode != 'LB_auto_manual_Manual')";
                                type "lbox_off_on";
                            }
                            leaf "RR_ComProt_PPP_ComprBsdRxSize" {
                                when "not ((./../../Protocol_PPP/RR_ComProt_PPP_ComprNegMode != 'LB_auto_manual_Manual') or (./../../Protocol_PPP/RR_ComProt_PPP_ComprCtrlProtEn != 'On'))";
                                type "uint8";
                                must ". = '0' or (. >= 9 and . <= 15)" {
                                    error-message "valmsg_it_PPP_ComprBsdRxSize";
                                }
                            }
                            leaf "RR_ComProt_PPP_ComprBsdTxSize" {
                                when "not ((./../../Protocol_PPP/RR_ComProt_PPP_ComprNegMode != 'LB_auto_manual_Manual') or (./../../Protocol_PPP/RR_ComProt_PPP_ComprCtrlProtEn != 'On'))";
                                type "uint8";
                                must ". = '0' or (. >= 9 and . <= 15)" {
                                    error-message "valmsg_it_PPP_ComprBsdTxSize";
                                }
                            }
                            leaf "RR_ComProt_PPP_ComprDeflateRxSize" {
                                when "not ((./../../Protocol_PPP/RR_ComProt_PPP_ComprNegMode != 'LB_auto_manual_Manual') or (./../../Protocol_PPP/RR_ComProt_PPP_ComprCtrlProtEn != 'On'))";
                                type "uint8";
                                must ". = '0' or (. >= 9 and . <= 15)" {
                                    error-message "valmsg_it_PPP_ComprDeflateRxSize";
                                }
                            }
                            leaf "RR_ComProt_PPP_ComprDeflateTxSize" {
                                when "not ((./../../Protocol_PPP/RR_ComProt_PPP_ComprNegMode != 'LB_auto_manual_Manual') or (./../../Protocol_PPP/RR_ComProt_PPP_ComprCtrlProtEn != 'On'))";
                                type "uint8";
                                must ". = '0' or (. >= 9 and . <= 15)" {
                                    error-message "valmsg_it_PPP_ComprDeflateTxSize";
                                }
                            }
                            leaf "RR_ComProt_PPP_DeviceType" {
                                type "enumeration" {
                                    enum "LB_com_port_dev_type_General" {
                                        value "0";
                                    }
                                    enum "LB_com_port_dev_type_Tetra_Mtm5x00" {
                                        value "1";
                                    }
                                }
                            }
                            leaf "RR_ComProt_PPP_NegotiateNetAddr" {
                                type "enumeration" {
                                    enum "Off" {
                                        value "0";
                                    }
                                    enum "On" {
                                        value "1";
                                    }
                                }
                                must "not ((. = 'Off' and (./../../Protocol_PPP/RR_ComProt_PPP_DeviceType = 'LB_com_port_dev_type_Tetra_Mtm5x00')))";
                            }
                            leaf "RR_ComProt_PPP_Masquerade" {
                                type "enumeration" {
                                    enum "Off" {
                                        value "0";
                                    }
                                    enum "On" {
                                        value "1";
                                    }
                                }
                                must "not ((. = 'On' and (./../../Protocol_PPP/RR_ComProt_PPP_NegotiateNetAddr != 'On')))";
                            }
                            leaf "RR_ComProt_PPP_RmtAccEn" {
                                when "not (/config_data/main/UserAccess/RR_UsAcc_RmtAccess_Enable != 'On')";
                                type "lbox_off_on";
                            }
                        }
                    }
                }
            }
        }
        grouping "TermServerProtocol" {
            choice "ch-TermServerProtocol" {
                case "c-None" {
                    when "deref(./_variant_source_ref) = \"None\"";
                }
                case "c-Async_Link" {
                    when "deref(./_variant_source_ref) = \"Async_Link\"";
                    container "Async_Link" {
                        container "Protocol_AsyncLink" {
                            leaf "RR_ComProt_DstIP" {
                                type "inet:ipv4-address";
                            }
                            leaf "RR_ComProt_DstPort" {
                                when "not (./../../Protocol_AsyncLink/RR_ComProt_DstStdPort != 'MANUAL')";
                                type "lim_udp_port0";
                            }
                            leaf "RR_ComProt_DstStdPort" {
                                type "lbox_udp_reserved_ports";
                            }
                            leaf "RR_ComProt_AsyncBcastAll" {
                                when "not (/config_data/device/DeviceHw/RR_DynHw_Primary_Radio != 'On')";
                                type "lbox_off_on";
                            }
                            leaf "RR_ComProt_AsyncBcastRx" {
                                when "not (/config_data/device/DeviceHw/RR_DynHw_Primary_Radio != 'On')";
                                type "lbox_off_on";
                            }
                        }
                    }
                }
                case "c-DNP3" {
                    when "deref(./_variant_source_ref) = \"DNP3\"";
                    container "DNP3" {
                        container "Protocol_DNP3" {
                            leaf "RR_ComProt_DNP3_AtrmIpBase" {
                                when "not (./../../Protocol_DNP3/RR_ComProt_DNP3_AtrMethod = 'Table')";
                                type "inet:ipv4-address";
                            }
                            leaf "RR_ComProt_DNP3_AtrmUdpPort" {
                                when "not ((./../../Protocol_DNP3/RR_ComProt_DNP3_AtrMethod = 'Table') or (./../../Protocol_DNP3/RR_ComProt_DNP3_DstStdPort != 'MANUAL'))";
                                type "lim_udp_port";
                            }
                            leaf "RR_ComProt_DNP3_AtrMethod" {
                                type "lbox_com_prot_addr_mode";
                            }
                            leaf "RR_ComProt_DNP3_AtrmIpMask" {
                                when "not (./../../Protocol_DNP3/RR_ComProt_DNP3_AtrMethod = 'Table')";
                                type "lim_ipv4_mask";
                            }
                            leaf "RR_ComProt_DNP3_DstStdPort" {
                                when "not (./../../Protocol_DNP3/RR_ComProt_DNP3_AtrMethod = 'Table')";
                                type "lbox_udp_reserved_ports";
                            }
                            leaf "RR_ComProt_DNP3_Bcast" {
                                when "not (/config_data/device/DeviceHw/RR_DynHw_Primary_Radio != 'On')";
                                type "lbox_off_on";
                            }
                        }
                        list "RR_S_TABLE_Protocol_DNP3_TTable" {
                            when "not (./../Protocol_DNP3/RR_ComProt_DNP3_AtrMethod = 'Mask')";
                            key "ID";
                            max-elements "1024";
                            ordered-by "user";
                            leaf "ID" {
                                type "lim_uint_16";
                            }
                            leaf "TTEntry_DNP3_Ena" {
                                type "lbox_off_on";
                                default "On";
                            }
                            leaf "TTEntry_DNP3_Note" {
                                type "string" {
                                    pattern "[^\"`\\\\$;]{0,42}";
                                }
                                default "";
                            }
                            leaf "TTEntry_DNP3_DevAddr_2B" {
                                type "lim_uint_16";
                                must ". <= ../TTEntry_DNP3_DevAddrLast_2B" {
                                    error-message "valmsg_it_TTEntry_DNP3_DevAddr_2B";
                                }
                                default "1";
                            }
                            leaf "TTEntry_DNP3_DevAddrLast_2B" {
                                type "lim_uint_16";
                                must ". >= ../TTEntry_DNP3_DevAddr_2B" {
                                    error-message "valmsg_it_TTEntry_DNP3_DevAddrLast_2B";
                                }
                                default "1";
                            }
                            leaf "TTEntry_DNP3_IpAddr" {
                                type "inet:ipv4-address";
                                default "0.0.0.0";
                            }
                            leaf "TTEntry_DNP3_IpInt" {
                                type "lbox_off_on";
                                default "Off";
                            }
                            leaf "TTEntry_DNP3_StdPort" {
                                type "lbox_udp_reserved_ports";
                                default "COM1";
                            }
                            leaf "TTEntry_DNP3_ManPort" {
                                when "not (../TTEntry_DNP3_StdPort != 'MANUAL')";
                                type "lim_udp_port";
                                default "50000";
                            }
                        }
                    }
                }
                case "c-DF1" {
                    when "deref(./_variant_source_ref) = \"DF1\"";
                    container "DF1" {
                        container "Protocol_DF1" {
                            leaf "RR_ComProt_DF1_AtrMethod" {
                                type "lbox_com_prot_addr_mode";
                            }
                            leaf "RR_ComProt_DF1_Mode" {
                                when "not (./../../Protocol_DF1/RR_ComProt_DF1_DuplexMode = 'Full duplex')";
                                type "lbox_com_prot_mode";
                            }
                            leaf "RR_ComProt_DF1_ChecksumMode" {
                                type "enumeration" {
                                    enum "BCC" {
                                        value "0";
                                    }
                                    enum "CRC" {
                                        value "1";
                                    }
                                }
                            }
                            leaf "RR_ComProt_DF1_DuplexMode" {
                                type "enumeration" {
                                    enum "Full duplex" {
                                        value "0";
                                    }
                                    enum "Half duplex" {
                                        value "1";
                                    }
                                }
                                must "not ((. = 'Half duplex' and (/config_data/auth/CnfAuth/RR_CnfAuthCnfVersion >= 0)))";
                            }
                            leaf "RR_ComProt_DF1_Bcast" {
                                when "not (/config_data/device/DeviceHw/RR_DynHw_Primary_Radio != 'On')";
                                type "lbox_off_on";
                            }
                            leaf "RR_ComProt_DF1_AtrmIpBase" {
                                when "not (./../../Protocol_DF1/RR_ComProt_DF1_AtrMethod = 'Table')";
                                type "inet:ipv4-address";
                            }
                            leaf "RR_ComProt_DF1_AtrmUdpPort" {
                                when "not ((./../../Protocol_DF1/RR_ComProt_DF1_AtrMethod = 'Table') or (./../../Protocol_DF1/RR_ComProt_DF1_DstStdPort != 'MANUAL'))";
                                type "lim_udp_port";
                            }
                            leaf "RR_ComProt_DF1_AtrmIpMask" {
                                when "not (./../../Protocol_DF1/RR_ComProt_DF1_AtrMethod = 'Table')";
                                type "lim_ipv4_mask";
                            }
                            leaf "RR_ComProt_DF1_DstStdPort" {
                                when "not (./../../Protocol_DF1/RR_ComProt_DF1_AtrMethod = 'Table')";
                                type "lbox_udp_reserved_ports";
                            }
                            leaf "RR_ComProt_DF1_LocAckEna" {
                                type "lbox_off_on";
                            }
                            leaf "RR_ComProt_DF1_Repeats" {
                                when "not (./../../Protocol_DF1/RR_ComProt_DF1_LocAckEna != 'On')";
                                type "uint8" {
                                    range "0..31";
                                }
                            }
                            leaf "RR_ComProt_DF1_AckTimeout" {
                                when "not (./../../Protocol_DF1/RR_ComProt_DF1_LocAckEna != 'On')";
                                type "uint16" {
                                    range "0..16383";
                                }
                            }
                        }
                        list "RR_S_TABLE_Protocol_DF1_TTable" {
                            when "not (./../Protocol_DF1/RR_ComProt_DF1_AtrMethod = 'Mask')";
                            key "ID";
                            max-elements "1024";
                            ordered-by "user";
                            leaf "ID" {
                                type "lim_uint_16";
                            }
                            leaf "TTEntry_DF1_Ena" {
                                type "lbox_off_on";
                                default "On";
                            }
                            leaf "TTEntry_DF1_Note" {
                                type "string" {
                                    pattern "[^\"`\\\\$;]{0,42}";
                                }
                                default "";
                            }
                            leaf "TTEntry_DF1_DevAddr_1B" {
                                type "lim_uint_8";
                                must ". <= ../TTEntry_DF1_DevAddrLast_1B" {
                                    error-message "valmsg_it_TTEntry_DF1_DevAddr";
                                }
                                default "1";
                            }
                            leaf "TTEntry_DF1_DevAddrLast_1B" {
                                type "lim_uint_8";
                                must ". >= ../TTEntry_DF1_DevAddr_1B" {
                                    error-message "valmsg_it_TTEntry_DF1_DevAddrLast";
                                }
                                default "1";
                            }
                            leaf "TTEntry_DF1_IpAddr" {
                                type "inet:ipv4-address";
                                default "0.0.0.0";
                            }
                            leaf "TTEntry_DF1_IpInt" {
                                type "lbox_off_on";
                                default "Off";
                            }
                            leaf "TTEntry_DF1_StdPort" {
                                type "lbox_udp_reserved_ports";
                                default "COM1";
                            }
                            leaf "TTEntry_DF1_ManPort" {
                                when "not (../TTEntry_DF1_StdPort != 'MANUAL')";
                                type "lim_udp_port";
                                default "50000";
                            }
                        }
                    }
                }
                case "c-Transparent" {
                    when "deref(./_variant_source_ref) = \"Transparent\"";
                }
                case "c-IEC101" {
                    when "deref(./_variant_source_ref) = \"IEC101\"";
                    container "IEC101" {
                        container "Protocol_IEC101" {
                            leaf "RR_ComProt_IEC101_Mode" {
                                type "enumeration" {
                                    enum "Primary" {
                                        value "0";
                                    }
                                    enum "Secondary" {
                                        value "1";
                                    }
                                    enum "Combined" {
                                        value "2";
                                    }
                                }
                                must "not ((. = 'Combined' and (/config_data/auth/CnfAuth/RR_CnfAuthCnfVersion >= 0)))";
                            }
                            leaf "RR_ComProt_IEC101_AddrMode" {
                                type "enumeration" {
                                    enum "8bit" {
                                        value "0";
                                    }
                                    enum "16bit" {
                                        value "1";
                                    }
                                    enum "8bit w/o ctrl byte" {
                                        value "2";
                                    }
                                    enum "8bit swp ctrl byte" {
                                        value "3";
                                    }
                                    enum "No addr" {
                                        value "4";
                                    }
                                }
                                must "not ((. = 'No addr' and (./../../Protocol_IEC101/RR_ComProt_IEC101_Mode != 'Combined')))";
                            }
                            leaf "RR_ComProt_IEC101_Bcast" {
                                when "not (/config_data/device/DeviceHw/RR_DynHw_Primary_Radio != 'On')";
                                type "lbox_off_on";
                            }
                            leaf "RR_ComProt_IEC101_AtrmIpBase" {
                                when "not ((./../../Protocol_IEC101/RR_ComProt_IEC101_AtrMethod = 'Table') or (./../../Protocol_IEC101/RR_ComProt_IEC101_Mode = 'Secondary'))";
                                type "inet:ipv4-address";
                            }
                            leaf "RR_ComProt_IEC101_AtrmUdpPort" {
                                when "not (((./../../Protocol_IEC101/RR_ComProt_IEC101_Mode != 'Secondary') and ((./../../Protocol_IEC101/RR_ComProt_IEC101_AtrMethod = 'Table') or (./../../Protocol_IEC101/RR_ComProt_IEC101_DstStdPort != 'MANUAL'))) or ((./../../Protocol_IEC101/RR_ComProt_IEC101_Mode != 'Primary') and ((./../../Protocol_IEC101/RR_ComProt_IEC101_SlaveDst = 'LASTRCV') or (./../../Protocol_IEC101/RR_ComProt_IEC101_DstStdPort != 'MANUAL'))))";
                                type "lim_udp_port";
                            }
                            leaf "RR_ComProt_IEC101_AtrMethod" {
                                when "not (./../../Protocol_IEC101/RR_ComProt_IEC101_Mode = 'Secondary')";
                                type "lbox_com_prot_addr_mode";
                            }
                            leaf "RR_ComProt_IEC101_AtrmIpMask" {
                                when "not ((./../../Protocol_IEC101/RR_ComProt_IEC101_AtrMethod = 'Table') or (./../../Protocol_IEC101/RR_ComProt_IEC101_Mode = 'Secondary'))";
                                type "lim_ipv4_mask";
                            }
                            leaf "RR_ComProt_IEC101_DstStdPort" {
                                when "not (((./../../Protocol_IEC101/RR_ComProt_IEC101_Mode = 'Primary') and (./../../Protocol_IEC101/RR_ComProt_IEC101_AtrMethod = 'Table')) or ((./../../Protocol_IEC101/RR_ComProt_IEC101_Mode = 'Secondary') and (./../../Protocol_IEC101/RR_ComProt_IEC101_SlaveDst = 'LASTRCV')))";
                                type "lbox_udp_reserved_ports";
                            }
                            leaf "RR_ComProt_IEC101_SlaveDst" {
                                when "not (./../../Protocol_IEC101/RR_ComProt_IEC101_Mode = 'Primary')";
                                type "lbox_com_prot_slave_dst";
                            }
                            leaf "RR_ComProt_IEC101_TsDropBcast" {
                                when "not ((./../../Protocol_IEC101/RR_ComProt_IEC101_Mode != 'Primary') or (./../../Protocol_IEC101/RR_ComProt_IEC101_Bcast != 'On') or (./../../Protocol_IEC101/RR_ComProt_IEC101_AddrMode = '8bit w/o ctrl byte'))";
                                type "lbox_off_on";
                            }
                            leaf "RR_ComProt_IEC101_TsEnable" {
                                when "not ((./../../Protocol_IEC101/RR_ComProt_IEC101_Mode != 'Secondary') or (./../../Protocol_IEC101/RR_ComProt_IEC101_AddrMode = '8bit w/o ctrl byte'))";
                                type "lbox_off_on";
                            }
                            leaf "RR_ComProt_IEC101_SpEnable" {
                                when "not ((./../../Protocol_IEC101/RR_ComProt_IEC101_Mode != 'Secondary') or (./../../Protocol_IEC101/RR_ComProt_IEC101_AddrMode = '8bit w/o ctrl byte'))";
                                type "lbox_off_on";
                            }
                            leaf "RR_ComProt_IEC101_SlaveTargetIp" {
                                when "not ((./../../Protocol_IEC101/RR_ComProt_IEC101_Mode = 'Primary') or ((./../../Protocol_IEC101/RR_ComProt_IEC101_Mode = 'Secondary') and (./../../Protocol_IEC101/RR_ComProt_IEC101_SlaveDst = 'LASTRCV')))";
                                type "inet:ipv4-address";
                            }
                            leaf "RR_ComProt_IEC101_UsedProtAddr" {
                                when "not ((./../../Protocol_IEC101/RR_ComProt_IEC101_Mode != 'Secondary') or (./../../Protocol_IEC101/RR_ComProt_IEC101_AddrMode = '8bit w/o ctrl byte') or ((./../../Protocol_IEC101/RR_ComProt_IEC101_TsEnable != 'On') and (./../../Protocol_IEC101/RR_ComProt_IEC101_SpEnable != 'On')))";
                                type "lim_uint_16";
                            }
                            leaf "RR_ComProt_IEC101_SlaveId" {
                                when "not ((./../../Protocol_IEC101/RR_ComProt_IEC101_Mode != 'Secondary') or (./../../Protocol_IEC101/RR_ComProt_IEC101_AddrMode = '8bit w/o ctrl byte') or (./../../Protocol_IEC101/RR_ComProt_IEC101_SpEnable != 'On'))";
                                type "lim_uint_8";
                            }
                            leaf "RR_ComProt_IEC101_SubgroupId" {
                                when "not ((./../../Protocol_IEC101/RR_ComProt_IEC101_Mode != 'Secondary') or (./../../Protocol_IEC101/RR_ComProt_IEC101_AddrMode = '8bit w/o ctrl byte') or (./../../Protocol_IEC101/RR_ComProt_IEC101_SpEnable != 'On'))";
                                type "lim_uint_8";
                            }
                            leaf "RR_ComProt_IEC101_SpPollPeriod" {
                                when "not ((./../../Protocol_IEC101/RR_ComProt_IEC101_Mode != 'Secondary') or (./../../Protocol_IEC101/RR_ComProt_IEC101_AddrMode = '8bit w/o ctrl byte') or (./../../Protocol_IEC101/RR_ComProt_IEC101_SpEnable != 'On'))";
                                type "uint16" {
                                    range "10..60000";
                                }
                            }
                            leaf "RR_ComProt_IEC101_SpTsPeriod" {
                                when "not ((./../../Protocol_IEC101/RR_ComProt_IEC101_Mode != 'Secondary') or (./../../Protocol_IEC101/RR_ComProt_IEC101_AddrMode = '8bit w/o ctrl byte') or (./../../Protocol_IEC101/RR_ComProt_IEC101_SpEnable != 'On') or (./../../Protocol_IEC101/RR_ComProt_IEC101_TsEnable != 'On'))";
                                type "lim_uint_8";
                            }
                            leaf "RR_ComProt_IEC101_NetRepeatTime" {
                                when "not ((./../../Protocol_IEC101/RR_ComProt_IEC101_Mode != 'Secondary') or (./../../Protocol_IEC101/RR_ComProt_IEC101_AddrMode = '8bit w/o ctrl byte') or (./../../Protocol_IEC101/RR_ComProt_IEC101_SpEnable != 'On'))";
                                type "uint16" {
                                    range "10..60000";
                                }
                            }
                            leaf "RR_ComProt_IEC101_PortRepeatTime" {
                                when "not ((./../../Protocol_IEC101/RR_ComProt_IEC101_Mode != 'Secondary') or (./../../Protocol_IEC101/RR_ComProt_IEC101_AddrMode = '8bit w/o ctrl byte') or ((./../../Protocol_IEC101/RR_ComProt_IEC101_TsEnable != 'On') and (./../../Protocol_IEC101/RR_ComProt_IEC101_SpEnable != 'On')))";
                                type "uint16" {
                                    range "10..60000";
                                }
                            }
                            leaf "RR_ComProt_IEC101_PortRepeatCount" {
                                when "not ((./../../Protocol_IEC101/RR_ComProt_IEC101_Mode != 'Secondary') or (./../../Protocol_IEC101/RR_ComProt_IEC101_AddrMode = '8bit w/o ctrl byte') or ((./../../Protocol_IEC101/RR_ComProt_IEC101_TsEnable != 'On') and (./../../Protocol_IEC101/RR_ComProt_IEC101_SpEnable != 'On')))";
                                type "lim_uint_8";
                            }
                        }
                        list "RR_S_TABLE_Protocol_IEC101_TTable" {
                            when "not ((./../Protocol_IEC101/RR_ComProt_IEC101_AtrMethod = 'Mask') or (./../Protocol_IEC101/RR_ComProt_IEC101_Mode = 'Secondary'))";
                            key "ID";
                            max-elements "1024";
                            ordered-by "user";
                            leaf "ID" {
                                type "lim_uint_16";
                            }
                            leaf "TTEntry_IEC101_Ena" {
                                type "lbox_off_on";
                                default "On";
                            }
                            leaf "TTEntry_IEC101_Note" {
                                type "string" {
                                    pattern "[^\"`\\\\$;]{0,42}";
                                }
                                default "";
                            }
                            leaf "TTEntry_IEC101_DevAddr_2B" {
                                type "lim_uint_16";
                                must ". <= ../TTEntry_IEC101_DevAddrLast_2B" {
                                    error-message "valmsg_it_TTEntry_IEC101_DevAddr_2B";
                                }
                                default "1";
                            }
                            leaf "TTEntry_IEC101_DevAddrLast_2B" {
                                type "lim_uint_16";
                                must ". >= ../TTEntry_IEC101_DevAddr_2B" {
                                    error-message "valmsg_it_TTEntry_IEC101_DevAddr_2B";
                                }
                                default "1";
                            }
                            leaf "TTEntry_IEC101_IpAddr" {
                                type "inet:ipv4-address";
                                default "0.0.0.0";
                            }
                            leaf "TTEntry_IEC101_IpInt" {
                                type "lbox_off_on";
                                default "Off";
                            }
                            leaf "TTEntry_IEC101_StdPort" {
                                type "lbox_udp_reserved_ports";
                                default "COM1";
                            }
                            leaf "TTEntry_IEC101_ManPort" {
                                when "not (../TTEntry_IEC101_StdPort != 'MANUAL')";
                                type "lim_udp_port";
                                default "50000";
                            }
                        }
                    }
                }
                case "c-UNI" {
                    when "deref(./_variant_source_ref) = \"UNI\"";
                    container "UNI" {
                        container "Protocol_UNI" {
                            leaf "RR_ComProt_UNI_PollResponseCtrl" {
                                when "not (./../../Protocol_UNI/RR_ComProt_UNI_Mode != 'Master')";
                                type "lbox_off_on";
                            }
                            leaf "RR_ComProt_UNI_Mode" {
                                type "lbox_com_prot_mode";
                            }
                            leaf "RR_ComProt_UNI_AddrMode" {
                                when "not (./../../Protocol_UNI/RR_ComProt_UNI_Mode != 'Master')";
                                type "enumeration" {
                                    enum "bin_1B" {
                                        value "0";
                                    }
                                    enum "ascii_2B" {
                                        value "1";
                                    }
                                    enum "bin_2B_LSB" {
                                        value "2";
                                    }
                                    enum "bin_2B_MSB" {
                                        value "3";
                                    }
                                }
                            }
                            leaf "RR_ComProt_UNI_Bcast" {
                                when "not (/config_data/device/DeviceHw/RR_DynHw_Primary_Radio != 'On')";
                                type "lbox_off_on";
                            }
                            leaf "RR_ComProt_UNI_AddrPos" {
                                when "not (./../../Protocol_UNI/RR_ComProt_UNI_Mode != 'Master')";
                                type "lim_uint_8_1toFF";
                            }
                            leaf "RR_ComProt_UNI_AddressMask" {
                                when "not ((./../../Protocol_UNI/RR_ComProt_UNI_Mode != 'Master') or (./../../Protocol_UNI/RR_ComProt_UNI_AddrMode = 'bin_1B' and ./../../Protocol_UNI/RR_ComProt_UNI_AddrMode = 'ascii_2B'))";
                                type "lim_uint_16";
                            }
                            leaf "RR_ComProt_UNI_BcastAddress" {
                                when "not ((/config_data/device/DeviceHw/RR_DynHw_Primary_Radio != 'On') or (./../../Protocol_UNI/RR_ComProt_UNI_Mode != 'Master') or (./../../Protocol_UNI/RR_ComProt_UNI_Bcast != 'On'))";
                                type "lim_uint_16";
                            }
                            leaf "RR_ComProt_UNI_AtrmIpBase" {
                                when "not ((./../../Protocol_UNI/RR_ComProt_UNI_Mode != 'Master') or (./../../Protocol_UNI/RR_ComProt_UNI_AtrMethod = 'Table'))";
                                type "inet:ipv4-address";
                            }
                            leaf "RR_ComProt_UNI_AtrmUdpPort" {
                                when "not ((./../../Protocol_UNI/RR_ComProt_UNI_AtrMethod = 'Table') or (./../../Protocol_UNI/RR_ComProt_UNI_DstStdPort != 'MANUAL'))";
                                type "lim_udp_port";
                            }
                            leaf "RR_ComProt_UNI_AtrMethod" {
                                when "not (./../../Protocol_UNI/RR_ComProt_UNI_Mode != 'Master')";
                                type "lbox_com_prot_addr_mode";
                            }
                            leaf "RR_ComProt_UNI_AtrmIpMask" {
                                when "not ((./../../Protocol_UNI/RR_ComProt_UNI_Mode != 'Master') or (./../../Protocol_UNI/RR_ComProt_UNI_AtrMethod = 'Table'))";
                                type "lim_ipv4_mask";
                            }
                            leaf "RR_ComProt_UNI_DstStdPort" {
                                when "not ((./../../Protocol_UNI/RR_ComProt_UNI_Mode != 'Master') or (./../../Protocol_UNI/RR_ComProt_UNI_AtrMethod = 'Table'))";
                                type "lbox_udp_reserved_ports";
                            }
                        }
                        list "RR_S_TABLE_Protocol_UNI_TTable" {
                            when "not ((./../Protocol_UNI/RR_ComProt_UNI_AtrMethod = 'Mask') or (./../Protocol_UNI/RR_ComProt_UNI_Mode = 'Slave'))";
                            key "ID";
                            max-elements "1024";
                            ordered-by "user";
                            leaf "ID" {
                                type "lim_uint_16";
                            }
                            leaf "TTEntry_UNI_Ena" {
                                type "lbox_off_on";
                                default "On";
                            }
                            leaf "TTEntry_UNI_Note" {
                                type "string" {
                                    pattern "[^\"`\\\\$;]{0,42}";
                                }
                                default "";
                            }
                            leaf "TTEntry_UNI_DevAddr_2B" {
                                type "lim_uint_16";
                                must ". <= ../TTEntry_UNI_DevAddrLast_2B" {
                                    error-message "valmsg_it_TTEntry_UNI_DevAddr_2B";
                                }
                                default "1";
                            }
                            leaf "TTEntry_UNI_DevAddrLast_2B" {
                                type "lim_uint_16";
                                must ". >= ../TTEntry_UNI_DevAddr_2B" {
                                    error-message "valmsg_it_TTEntry_UNI_DevAddr_2B";
                                }
                                default "1";
                            }
                            leaf "TTEntry_UNI_IpAddr" {
                                type "inet:ipv4-address";
                                default "0.0.0.0";
                            }
                            leaf "TTEntry_UNI_IpInt" {
                                type "lbox_off_on";
                                default "Off";
                            }
                            leaf "TTEntry_UNI_StdPort" {
                                type "lbox_udp_reserved_ports";
                                default "COM1";
                            }
                            leaf "TTEntry_UNI_ManPort" {
                                when "not (../TTEntry_UNI_StdPort != 'MANUAL')";
                                type "lim_udp_port";
                                default "50000";
                            }
                        }
                    }
                }
                case "c-RDS" {
                    when "deref(./_variant_source_ref) = \"RDS\"";
                    container "RDS" {
                        container "Protocol_RDS" {
                            leaf "RR_ComProt_RDS_AckEna" {
                                type "lbox_off_on";
                            }
                            leaf "RR_ComProt_RDS_Repeats" {
                                when "not (./../../Protocol_RDS/RR_ComProt_RDS_AckEna != 'On')";
                                type "uint8" {
                                    range "0..31";
                                }
                            }
                            leaf "RR_ComProt_RDS_AckTimeout" {
                                when "not (./../../Protocol_RDS/RR_ComProt_RDS_AckEna != 'On')";
                                type "uint16" {
                                    range "0..16383";
                                }
                            }
                            leaf "RR_ComProt_RDS_AtrmIpBase" {
                                when "not (./../../Protocol_RDS/RR_ComProt_RDS_AtrMethod = 'Table')";
                                type "inet:ipv4-address";
                            }
                            leaf "RR_ComProt_RDS_AtrmUdpPort" {
                                when "not ((./../../Protocol_RDS/RR_ComProt_RDS_AtrMethod = 'Table') or (./../../Protocol_RDS/RR_ComProt_RDS_DstStdPort != 'MANUAL'))";
                                type "lim_udp_port";
                            }
                            leaf "RR_ComProt_RDS_AtrMethod" {
                                type "lbox_com_prot_addr_mode";
                            }
                            leaf "RR_ComProt_RDS_AtrmIpMask" {
                                when "not (./../../Protocol_RDS/RR_ComProt_RDS_AtrMethod = 'Table')";
                                type "lim_ipv4_mask";
                            }
                            leaf "RR_ComProt_RDS_DstStdPort" {
                                when "not (./../../Protocol_RDS/RR_ComProt_RDS_AtrMethod = 'Table')";
                                type "lbox_udp_reserved_ports";
                            }
                            leaf "RR_ComProt_RDS_LocRespAddr" {
                                type "lim_uint_8";
                            }
                        }
                        list "RR_S_TABLE_Protocol_RDS_TTable" {
                            when "not (./../Protocol_RDS/RR_ComProt_RDS_AtrMethod = 'Mask')";
                            key "ID";
                            max-elements "1024";
                            ordered-by "user";
                            leaf "ID" {
                                type "lim_uint_16";
                            }
                            leaf "TTEntry_RDS_Ena" {
                                type "lbox_off_on";
                                default "On";
                            }
                            leaf "TTEntry_RDS_Note" {
                                type "string" {
                                    pattern "[^\"`\\\\$;]{0,42}";
                                }
                                default "";
                            }
                            leaf "TTEntry_RDS_DevAddr_1B" {
                                type "lim_uint_8";
                                must ". <= ../TTEntry_RDS_DevAddrLast_1B" {
                                    error-message "valmsg_it_TTEntry_RDS_DevAddr_1B";
                                }
                                default "1";
                            }
                            leaf "TTEntry_RDS_DevAddrLast_1B" {
                                type "lim_uint_8";
                                must ". >= ../TTEntry_RDS_DevAddr_1B" {
                                    error-message "valmsg_it_TTEntry_RDS_DevAddr_1B";
                                }
                                default "1";
                            }
                            leaf "TTEntry_RDS_IpAddr" {
                                type "inet:ipv4-address";
                                default "0.0.0.0";
                            }
                            leaf "TTEntry_RDS_IpInt" {
                                type "lbox_off_on";
                                default "Off";
                            }
                            leaf "TTEntry_RDS_StdPort" {
                                type "lbox_udp_reserved_ports";
                                default "COM1";
                            }
                            leaf "TTEntry_RDS_ManPort" {
                                when "not (../TTEntry_RDS_StdPort != 'MANUAL')";
                                type "lim_udp_port";
                                default "50000";
                            }
                        }
                    }
                }
                case "c-ModbusRTU" {
                    when "deref(./_variant_source_ref) = \"ModbusRTU\"";
                    container "ModbusRTU" {
                        container "Protocol_ModbusRTU" {
                            leaf "RR_ComProt_ModbusRTU_AtrmIpBase" {
                                when "not ((./../../Protocol_ModbusRTU/RR_ComProt_ModbusRTU_AtrMethod = 'Table') or (./../../Protocol_ModbusRTU/RR_ComProt_ModbusRTU_Mode = 'Slave'))";
                                type "inet:ipv4-address";
                            }
                            leaf "RR_ComProt_ModbusRTU_AtrmUdpPort" {
                                when "not ((./../../Protocol_ModbusRTU/RR_ComProt_ModbusRTU_AtrMethod = 'Table') or (./../../Protocol_ModbusRTU/RR_ComProt_ModbusRTU_DstStdPort != 'MANUAL'))";
                                type "lim_udp_port";
                            }
                            leaf "RR_ComProt_ModbusRTU_Mode" {
                                type "lbox_com_prot_mode";
                            }
                            leaf "RR_ComProt_ModbusRTU_Bcast" {
                                when "not (/config_data/device/DeviceHw/RR_DynHw_Primary_Radio != 'On')";
                                type "lbox_off_on";
                            }
                            leaf "RR_ComProt_ModbusRTU_AtrMethod" {
                                when "not (./../../Protocol_ModbusRTU/RR_ComProt_ModbusRTU_Mode = 'Slave')";
                                type "lbox_com_prot_addr_mode";
                            }
                            leaf "RR_ComProt_ModbusRTU_AtrmIpMask" {
                                when "not ((./../../Protocol_ModbusRTU/RR_ComProt_ModbusRTU_Mode = 'Slave') or (./../../Protocol_ModbusRTU/RR_ComProt_ModbusRTU_AtrMethod = 'Table'))";
                                type "lim_ipv4_mask";
                            }
                            leaf "RR_ComProt_ModbusRTU_DstStdPort" {
                                when "not (((./../../Protocol_ModbusRTU/RR_ComProt_ModbusRTU_Mode = 'Master') and (./../../Protocol_ModbusRTU/RR_ComProt_ModbusRTU_AtrMethod = 'Table')) or ((./../../Protocol_ModbusRTU/RR_ComProt_ModbusRTU_Mode = 'Slave') and (./../../Protocol_ModbusRTU/RR_ComProt_ModbusRTU_SlaveDst = 'LASTRCV')))";
                                type "lbox_udp_reserved_ports";
                            }
                            leaf "RR_ComProt_ModbusRTU_SlaveDst" {
                                when "not (./../../Protocol_ModbusRTU/RR_ComProt_ModbusRTU_Mode != 'Slave')";
                                type "lbox_com_prot_slave_dst";
                            }
                            leaf "RR_ComProt_ModbusRTU_BcastAddress" {
                                when "not ((/config_data/device/DeviceHw/RR_DynHw_Primary_Radio != 'On') or (./../../Protocol_ModbusRTU/RR_ComProt_ModbusRTU_Mode != 'Master') or (./../../Protocol_ModbusRTU/RR_ComProt_ModbusRTU_Bcast != 'On'))";
                                type "lim_uint_8";
                            }
                            leaf "RR_ComProt_ModbusRTU_ResponseTimeout" {
                                when "not (./../../Protocol_ModbusRTU/RR_ComProt_ModbusRTU_Mode != 'Slave')";
                                type "uint16" {
                                    range "0..8190";
                                }
                            }
                            leaf "RR_ComProt_ModbusRTU_SlaveTargetIp" {
                                when "not ((./../../Protocol_ModbusRTU/RR_ComProt_ModbusRTU_Mode = 'Master') or ((./../../Protocol_ModbusRTU/RR_ComProt_ModbusRTU_Mode = 'Slave') and (./../../Protocol_ModbusRTU/RR_ComProt_ModbusRTU_SlaveDst = 'LASTRCV')))";
                                type "inet:ipv4-address";
                            }
                        }
                        list "RR_S_TABLE_Protocol_ModbusRTU_TTable" {
                            when "not ((./../Protocol_ModbusRTU/RR_ComProt_ModbusRTU_AtrMethod = 'Mask') or (./../Protocol_ModbusRTU/RR_ComProt_ModbusRTU_Mode = 'Slave'))";
                            key "ID";
                            max-elements "1024";
                            ordered-by "user";
                            leaf "ID" {
                                type "lim_uint_16";
                            }
                            leaf "TTEntry_ModbusRTU_Ena" {
                                type "lbox_off_on";
                                default "On";
                            }
                            leaf "TTEntry_ModbusRTU_Note" {
                                type "string" {
                                    pattern "[^\"`\\\\$;]{0,42}";
                                }
                                default "";
                            }
                            leaf "TTEntry_ModbusRTU_DevAddr_1B" {
                                type "lim_uint_8";
                                must ". <= ../TTEntry_ModbusRTU_DevAddrLast_1B" {
                                    error-message "valmsg_it_TTEntry_ModbusRTU_DevAddr_1B";
                                }
                                default "1";
                            }
                            leaf "TTEntry_ModbusRTU_DevAddrLast_1B" {
                                type "lim_uint_8";
                                must ". >= ../TTEntry_ModbusRTU_DevAddr_1B" {
                                    error-message "valmsg_it_TTEntry_ModbusRTU_DevAddr_1B";
                                }
                                default "1";
                            }
                            leaf "TTEntry_ModbusRTU_IpAddr" {
                                type "inet:ipv4-address";
                                default "0.0.0.0";
                            }
                            leaf "TTEntry_ModbusRTU_IpInt" {
                                type "lbox_off_on";
                                default "Off";
                            }
                            leaf "TTEntry_ModbusRTU_StdPort" {
                                type "lbox_udp_reserved_ports";
                                default "COM1";
                            }
                            leaf "TTEntry_ModbusRTU_ManPort" {
                                when "not (../TTEntry_ModbusRTU_StdPort != 'MANUAL')";
                                type "lim_udp_port";
                                default "50000";
                            }
                        }
                    }
                }
                case "c-ModbusTCP" {
                    when "deref(./_variant_source_ref) = \"ModbusTCP\"";
                    container "ModbusTCP" {
                        container "Protocol_ModbusTCP" {
                            leaf "RR_ComProt_ModbusTCP_AtrmIpBase" {
                                when "not ((./../../Protocol_ModbusTCP/RR_ComProt_ModbusTCP_AtrMethod = 'Table') or (./../../Protocol_ModbusTCP/RR_ComProt_ModbusTCP_Mode = 'Slave'))";
                                type "inet:ipv4-address";
                            }
                            leaf "RR_ComProt_ModbusTCP_AtrmUdpPort" {
                                when "not ((./../../Protocol_ModbusTCP/RR_ComProt_ModbusTCP_AtrMethod = 'Table') or (./../../Protocol_ModbusTCP/RR_ComProt_ModbusTCP_DstStdPort != 'MANUAL'))";
                                type "lim_udp_port";
                            }
                            leaf "RR_ComProt_ModbusTCP_Mode" {
                                type "lbox_com_prot_mode";
                            }
                            leaf "RR_ComProt_ModbusTCP_Bcast" {
                                when "not (/config_data/device/DeviceHw/RR_DynHw_Primary_Radio != 'On')";
                                type "lbox_off_on";
                            }
                            leaf "RR_ComProt_ModbusTCP_AtrMethod" {
                                when "not (./../../Protocol_ModbusTCP/RR_ComProt_ModbusTCP_Mode = 'Slave')";
                                type "lbox_com_prot_addr_mode";
                            }
                            leaf "RR_ComProt_ModbusTCP_AtrmIpMask" {
                                when "not ((./../../Protocol_ModbusTCP/RR_ComProt_ModbusTCP_Mode = 'Slave') or (./../../Protocol_ModbusTCP/RR_ComProt_ModbusTCP_AtrMethod = 'Table'))";
                                type "lim_ipv4_mask";
                            }
                            leaf "RR_ComProt_ModbusTCP_DstStdPort" {
                                when "not (((./../../Protocol_ModbusTCP/RR_ComProt_ModbusTCP_Mode = 'Master') and (./../../Protocol_ModbusTCP/RR_ComProt_ModbusTCP_AtrMethod = 'Table')) or ((./../../Protocol_ModbusTCP/RR_ComProt_ModbusTCP_Mode = 'Slave') and (./../../Protocol_ModbusTCP/RR_ComProt_ModbusTCP_SlaveDst = 'LASTRCV')))";
                                type "lbox_udp_reserved_ports";
                            }
                            leaf "RR_ComProt_ModbusTCP_SlaveDst" {
                                when "not (./../../Protocol_ModbusTCP/RR_ComProt_ModbusTCP_Mode != 'Slave')";
                                type "lbox_com_prot_slave_dst";
                            }
                            leaf "RR_ComProt_ModbusTCP_BcastAddress" {
                                when "not ((/config_data/device/DeviceHw/RR_DynHw_Primary_Radio != 'On') or (./../../Protocol_ModbusTCP/RR_ComProt_ModbusTCP_Mode != 'Master') or (./../../Protocol_ModbusTCP/RR_ComProt_ModbusTCP_Bcast != 'On'))";
                                type "lim_uint_8";
                            }
                            leaf "RR_ComProt_ModbusTCP_SlaveTargetIp" {
                                when "not ((./../../Protocol_ModbusTCP/RR_ComProt_ModbusTCP_Mode = 'Master') or ((./../../Protocol_ModbusTCP/RR_ComProt_ModbusTCP_Mode = 'Slave') and (./../../Protocol_ModbusTCP/RR_ComProt_ModbusTCP_SlaveDst = 'LASTRCV')))";
                                type "inet:ipv4-address";
                            }
                        }
                        list "RR_S_TABLE_Protocol_ModbusTCP_TTable" {
                            when "not ((./../Protocol_ModbusTCP/RR_ComProt_ModbusTCP_AtrMethod = 'Mask') or (./../Protocol_ModbusTCP/RR_ComProt_ModbusTCP_Mode = 'Slave'))";
                            key "ID";
                            max-elements "1024";
                            ordered-by "user";
                            leaf "ID" {
                                type "lim_uint_16";
                            }
                            leaf "TTEntry_ModbusTCP_Ena" {
                                type "lbox_off_on";
                                default "On";
                            }
                            leaf "TTEntry_ModbusTCP_Note" {
                                type "string" {
                                    pattern "[^\"`\\\\$;]{0,42}";
                                }
                                default "";
                            }
                            leaf "TTEntry_ModbusTCP_DevAddr_1B" {
                                type "lim_uint_8";
                                must ". <= ../TTEntry_ModbusTCP_DevAddrLast_1B" {
                                    error-message "valmsg_it_TTEntry_ModbusTCP_DevAddr_1B";
                                }
                                default "1";
                            }
                            leaf "TTEntry_ModbusTCP_DevAddrLast_1B" {
                                type "lim_uint_8";
                                must ". >= ../TTEntry_ModbusTCP_DevAddr_1B" {
                                    error-message "valmsg_it_TTEntry_ModbusTCP_DevAddr_1B";
                                }
                                default "1";
                            }
                            leaf "TTEntry_ModbusTCP_IpAddr" {
                                type "inet:ipv4-address";
                                default "0.0.0.0";
                            }
                            leaf "TTEntry_ModbusTCP_IpInt" {
                                type "lbox_off_on";
                                default "Off";
                            }
                            leaf "TTEntry_ModbusTCP_StdPort" {
                                type "lbox_udp_reserved_ports";
                                default "COM1";
                            }
                            leaf "TTEntry_ModbusTCP_ManPort" {
                                when "not (../TTEntry_ModbusTCP_StdPort != 'MANUAL')";
                                type "lim_udp_port";
                                default "50000";
                            }
                        }
                    }
                }
                case "c-PR2000" {
                    when "deref(./_variant_source_ref) = \"PR2000\"";
                    container "PR2000" {
                        container "Protocol_PR2000" {
                            leaf "RR_ComProt_PR2000_AtrmIpBase" {
                                when "not ((./../../Protocol_PR2000/RR_ComProt_PR2000_AtrMethod = 'Table') or (./../../Protocol_PR2000/RR_ComProt_PR2000_Mode = 'Slave'))";
                                type "inet:ipv4-address";
                            }
                            leaf "RR_ComProt_PR2000_AtrmUdpPort" {
                                when "not ((./../../Protocol_PR2000/RR_ComProt_PR2000_AtrMethod = 'Table') or (./../../Protocol_PR2000/RR_ComProt_PR2000_DstStdPort != 'MANUAL'))";
                                type "lim_udp_port";
                            }
                            leaf "RR_ComProt_PR2000_Sync" {
                                type "lim_uint_16";
                            }
                            leaf "RR_ComProt_PR2000_Mode" {
                                type "lbox_com_prot_mode";
                            }
                            leaf "RR_ComProt_PR2000_Bcast" {
                                when "not (/config_data/device/DeviceHw/RR_DynHw_Primary_Radio != 'On')";
                                type "lbox_off_on";
                            }
                            leaf "RR_ComProt_PR2000_AtrMethod" {
                                when "not (./../../Protocol_PR2000/RR_ComProt_PR2000_Mode = 'Slave')";
                                type "lbox_com_prot_addr_mode";
                            }
                            leaf "RR_ComProt_PR2000_AtrmIpMask" {
                                when "not ((./../../Protocol_PR2000/RR_ComProt_PR2000_Mode = 'Slave') or (./../../Protocol_PR2000/RR_ComProt_PR2000_AtrMethod = 'Table'))";
                                type "lim_ipv4_mask";
                            }
                            leaf "RR_ComProt_PR2000_DstStdPort" {
                                when "not (((./../../Protocol_PR2000/RR_ComProt_PR2000_Mode = 'Master') and (./../../Protocol_PR2000/RR_ComProt_PR2000_AtrMethod = 'Table')) or ((./../../Protocol_PR2000/RR_ComProt_PR2000_Mode = 'Slave') and (./../../Protocol_PR2000/RR_ComProt_PR2000_SlaveDst = 'LASTRCV')))";
                                type "lbox_udp_reserved_ports";
                            }
                            leaf "RR_ComProt_PR2000_SlaveDst" {
                                when "not (./../../Protocol_PR2000/RR_ComProt_PR2000_Mode != 'Slave')";
                                type "lbox_com_prot_slave_dst";
                            }
                            leaf "RR_ComProt_PR2000_SlaveTargetIp" {
                                when "not ((./../../Protocol_PR2000/RR_ComProt_PR2000_Mode = 'Master') or ((./../../Protocol_PR2000/RR_ComProt_PR2000_Mode = 'Slave') and (./../../Protocol_PR2000/RR_ComProt_PR2000_SlaveDst = 'LASTRCV')))";
                                type "inet:ipv4-address";
                            }
                        }
                        list "RR_S_TABLE_Protocol_PR2000_TTable" {
                            when "not ((./../Protocol_PR2000/RR_ComProt_PR2000_AtrMethod = 'Mask') or (./../Protocol_PR2000/RR_ComProt_PR2000_Mode = 'Slave'))";
                            key "ID";
                            max-elements "1024";
                            ordered-by "user";
                            leaf "ID" {
                                type "lim_uint_16";
                            }
                            leaf "TTEntry_PR2000_Ena" {
                                type "lbox_off_on";
                                default "On";
                            }
                            leaf "TTEntry_PR2000_Note" {
                                type "string" {
                                    pattern "[^\"`\\\\$;]{0,42}";
                                }
                                default "";
                            }
                            leaf "TTEntry_PR2000_DevAddr_1B" {
                                type "lim_uint_8";
                                must ". <= ../TTEntry_PR2000_DevAddrLast_1B" {
                                    error-message "valmsg_it_TTEntry_PR2000_DevAddr_1B";
                                }
                                default "1";
                            }
                            leaf "TTEntry_PR2000_DevAddrLast_1B" {
                                type "lim_uint_8";
                                must ". >= ../TTEntry_PR2000_DevAddr_1B" {
                                    error-message "valmsg_it_TTEntry_PR2000_DevAddr_1B";
                                }
                                default "1";
                            }
                            leaf "TTEntry_PR2000_IpAddr" {
                                type "inet:ipv4-address";
                                default "0.0.0.0";
                            }
                            leaf "TTEntry_PR2000_IpInt" {
                                type "lbox_off_on";
                                default "Off";
                            }
                            leaf "TTEntry_PR2000_StdPort" {
                                type "lbox_udp_reserved_ports";
                                default "COM1";
                            }
                            leaf "TTEntry_PR2000_ManPort" {
                                when "not (../TTEntry_PR2000_StdPort != 'MANUAL')";
                                type "lim_udp_port";
                                default "50000";
                            }
                        }
                    }
                }
                case "c-S3964R" {
                    when "deref(./_variant_source_ref) = \"S3964R\"";
                    container "S3964R" {
                        container "Protocol_S3964R" {
                            leaf "RR_ComProt_S3964R_AtrmIpBase" {
                                when "not ((./../../Protocol_S3964R/RR_ComProt_S3964R_AtrMethod = 'Table') or (./../../Protocol_S3964R/RR_ComProt_S3964R_Mode = 'Slave'))";
                                type "inet:ipv4-address";
                            }
                            leaf "RR_ComProt_S3964R_AtrmUdpPort" {
                                when "not ((./../../Protocol_S3964R/RR_ComProt_S3964R_AtrMethod = 'Table') or (./../../Protocol_S3964R/RR_ComProt_S3964R_DstStdPort != 'MANUAL'))";
                                type "lim_udp_port";
                            }
                            leaf "RR_ComProt_S3964R_Mode" {
                                type "lbox_com_prot_mode";
                            }
                            leaf "RR_ComProt_S3964R_Bcast" {
                                when "not (/config_data/device/DeviceHw/RR_DynHw_Primary_Radio != 'On')";
                                type "lbox_off_on";
                            }
                            leaf "RR_ComProt_S3964R_AtrMethod" {
                                when "not (./../../Protocol_S3964R/RR_ComProt_S3964R_Mode = 'Slave')";
                                type "lbox_com_prot_addr_mode";
                            }
                            leaf "RR_ComProt_S3964R_AtrmIpMask" {
                                when "not ((./../../Protocol_S3964R/RR_ComProt_S3964R_Mode = 'Slave') or (./../../Protocol_S3964R/RR_ComProt_S3964R_AtrMethod = 'Table'))";
                                type "lim_ipv4_mask";
                            }
                            leaf "RR_ComProt_S3964R_DstStdPort" {
                                when "not (((./../../Protocol_S3964R/RR_ComProt_S3964R_Mode = 'Master') and (./../../Protocol_S3964R/RR_ComProt_S3964R_AtrMethod = 'Table')) or ((./../../Protocol_S3964R/RR_ComProt_S3964R_Mode = 'Slave') and (./../../Protocol_S3964R/RR_ComProt_S3964R_SlaveDst = 'LASTRCV')))";
                                type "lbox_udp_reserved_ports";
                            }
                            leaf "RR_ComProt_S3964R_SlaveDst" {
                                when "not (./../../Protocol_S3964R/RR_ComProt_S3964R_Mode != 'Slave')";
                                type "lbox_com_prot_slave_dst";
                            }
                            leaf "RR_ComProt_S3964R_AddrPos" {
                                when "not (./../../Protocol_S3964R/RR_ComProt_S3964R_Mode != 'Master')";
                                type "lim_uint_8_1toFF";
                            }
                            leaf "RR_ComProt_S3964R_BcastAddress" {
                                when "not ((/config_data/device/DeviceHw/RR_DynHw_Primary_Radio != 'On') or (./../../Protocol_S3964R/RR_ComProt_S3964R_Mode != 'Master') or (./../../Protocol_S3964R/RR_ComProt_S3964R_Bcast != 'On'))";
                                type "lim_uint_16";
                            }
                            leaf "RR_ComProt_S3964R_DLETimeout" {
                                type "uint16" {
                                    range "300..8190";
                                }
                            }
                            leaf "RR_ComProt_S3964R_Repeats" {
                                type "uint8" {
                                    range "0..7";
                                }
                            }
                            leaf "RR_ComProt_S3964R_AddrMode" {
                                when "not (./../../Protocol_S3964R/RR_ComProt_S3964R_Mode != 'Master')";
                                type "enumeration" {
                                    enum "bin_1B" {
                                        value "0";
                                    }
                                    enum "bin_2B_LSB" {
                                        value "1";
                                    }
                                    enum "bin_2B_MSB" {
                                        value "2";
                                    }
                                }
                            }
                            leaf "RR_ComProt_S3964R_BCC" {
                                type "lbox_off_on";
                            }
                            leaf "RR_ComProt_S3964R_Priority" {
                                type "enumeration" {
                                    enum "Low" {
                                        value "0";
                                    }
                                    enum "High" {
                                        value "1";
                                    }
                                }
                            }
                            leaf "RR_ComProt_S3964R_SlaveTargetIp" {
                                when "not ((./../../Protocol_S3964R/RR_ComProt_S3964R_Mode = 'Master') or ((./../../Protocol_S3964R/RR_ComProt_S3964R_Mode = 'Slave') and (./../../Protocol_S3964R/RR_ComProt_S3964R_SlaveDst = 'LASTRCV')))";
                                type "inet:ipv4-address";
                            }
                        }
                        list "RR_S_TABLE_Protocol_S3964R_TTable" {
                            when "not ((./../Protocol_S3964R/RR_ComProt_S3964R_AtrMethod = 'Mask') or (./../Protocol_S3964R/RR_ComProt_S3964R_Mode = 'Slave'))";
                            key "ID";
                            max-elements "1024";
                            ordered-by "user";
                            leaf "ID" {
                                type "lim_uint_16";
                            }
                            leaf "TTEntry_S3964R_Ena" {
                                type "lbox_off_on";
                                default "On";
                            }
                            leaf "TTEntry_S3964R_Note" {
                                type "string" {
                                    pattern "[^\"`\\\\$;]{0,42}";
                                }
                                default "";
                            }
                            leaf "TTEntry_S3964R_DevAddr_2B" {
                                type "lim_uint_16";
                                must ". <= ../TTEntry_S3964R_DevAddrLast_2B" {
                                    error-message "valmsg_it_TTEntry_S3964R_DevAddr_2B";
                                }
                                default "1";
                            }
                            leaf "TTEntry_S3964R_DevAddrLast_2B" {
                                type "lim_uint_16";
                                must ". >= ../TTEntry_S3964R_DevAddr_2B" {
                                    error-message "valmsg_it_TTEntry_S3964R_DevAddr_2B";
                                }
                                default "1";
                            }
                            leaf "TTEntry_S3964R_IpAddr" {
                                type "inet:ipv4-address";
                                default "0.0.0.0";
                            }
                            leaf "TTEntry_S3964R_IpInt" {
                                type "lbox_off_on";
                                default "Off";
                            }
                            leaf "TTEntry_S3964R_StdPort" {
                                type "lbox_udp_reserved_ports";
                                default "COM1";
                            }
                            leaf "TTEntry_S3964R_ManPort" {
                                when "not (../TTEntry_S3964R_StdPort != 'MANUAL')";
                                type "lim_udp_port";
                                default "50000";
                            }
                        }
                    }
                }
                case "c-SAIA_S-BUS" {
                    when "deref(./_variant_source_ref) = \"SAIA_S-BUS\"";
                    container "SAIA_S-BUS" {
                        container "Protocol_SAIA_SBUS" {
                            leaf "RR_ComProt_SAIA_SBUS_AtrmIpBase" {
                                when "not ((./../../Protocol_SAIA_SBUS/RR_ComProt_SAIA_SBUS_AtrMethod = 'Table') or (./../../Protocol_SAIA_SBUS/RR_ComProt_SAIA_SBUS_Mode = 'Slave'))";
                                type "inet:ipv4-address";
                            }
                            leaf "RR_ComProt_SAIA_SBUS_AtrmUdpPort" {
                                when "not ((./../../Protocol_SAIA_SBUS/RR_ComProt_SAIA_SBUS_AtrMethod = 'Table') or (./../../Protocol_SAIA_SBUS/RR_ComProt_SAIA_SBUS_DstStdPort != 'MANUAL'))";
                                type "lim_udp_port";
                            }
                            leaf "RR_ComProt_SAIA_SBUS_Mode" {
                                type "lbox_com_prot_mode_plus";
                            }
                            leaf "RR_ComProt_SAIA_SBUS_Bcast" {
                                when "not (/config_data/device/DeviceHw/RR_DynHw_Primary_Radio != 'On')";
                                type "lbox_off_on";
                            }
                            leaf "RR_ComProt_SAIA_SBUS_AtrMethod" {
                                when "not (./../../Protocol_SAIA_SBUS/RR_ComProt_SAIA_SBUS_Mode = 'Slave')";
                                type "lbox_com_prot_addr_mode";
                            }
                            leaf "RR_ComProt_SAIA_SBUS_AtrmIpMask" {
                                when "not ((./../../Protocol_SAIA_SBUS/RR_ComProt_SAIA_SBUS_Mode = 'Slave') or (./../../Protocol_SAIA_SBUS/RR_ComProt_SAIA_SBUS_AtrMethod = 'Table'))";
                                type "lim_ipv4_mask";
                            }
                            leaf "RR_ComProt_SAIA_SBUS_DstStdPort" {
                                when "not (((./../../Protocol_SAIA_SBUS/RR_ComProt_SAIA_SBUS_Mode = 'Master') and (./../../Protocol_SAIA_SBUS/RR_ComProt_SAIA_SBUS_AtrMethod = 'Table')) or ((./../../Protocol_SAIA_SBUS/RR_ComProt_SAIA_SBUS_Mode = 'SlavePlus') and (./../../Protocol_SAIA_SBUS/RR_ComProt_SAIA_SBUS_AtrMethod = 'Table')) or (./../../Protocol_SAIA_SBUS/RR_ComProt_SAIA_SBUS_Mode = 'Slave'))";
                                type "lbox_udp_reserved_ports";
                            }
                            leaf "RR_ComProt_SAIA_SBUS_SlaveDst" {
                                when "not (./../../Protocol_SAIA_SBUS/RR_ComProt_SAIA_SBUS_Mode = 'Master')";
                                type "lbox_com_prot_slave_dst";
                            }
                            leaf "RR_ComProt_SAIA_SBUS_SlaveTargetIp" {
                                when "not ((./../../Protocol_SAIA_SBUS/RR_ComProt_SAIA_SBUS_Mode = 'Master') or ((./../../Protocol_SAIA_SBUS/RR_ComProt_SAIA_SBUS_Mode = 'SlavePlus') and (./../../Protocol_SAIA_SBUS/RR_ComProt_SAIA_SBUS_SlaveDst = 'LASTRCV')) or ((./../../Protocol_SAIA_SBUS/RR_ComProt_SAIA_SBUS_Mode = 'Slave') and (./../../Protocol_SAIA_SBUS/RR_ComProt_SAIA_SBUS_SlaveDst = 'LASTRCV')))";
                                type "inet:ipv4-address";
                            }
                            leaf "RR_ComProt_SAIA_SBUS_RepeatTimeout" {
                                when "not (./../../Protocol_SAIA_SBUS/RR_ComProt_SAIA_SBUS_Mode = 'Master')";
                                type "uint16" {
                                    range "0..16383";
                                }
                            }
                            leaf "RR_ComProt_SAIA_SBUS_ResponseTimeoutCongestion" {
                                when "not (./../../Protocol_SAIA_SBUS/RR_ComProt_SAIA_SBUS_Mode != 'Master')";
                                type "lim_uint_16";
                            }
                            leaf "RR_ComProt_SAIA_SBUS_Repeats" {
                                when "not (./../../Protocol_SAIA_SBUS/RR_ComProt_SAIA_SBUS_Mode = 'Master')";
                                type "uint8" {
                                    range "0..7";
                                }
                            }
                            leaf "RR_ComProt_SAIA_SBUS_DstStdPortSlave" {
                                when "not ((./../../Protocol_SAIA_SBUS/RR_ComProt_SAIA_SBUS_Mode = 'Master') or ((./../../Protocol_SAIA_SBUS/RR_ComProt_SAIA_SBUS_Mode = 'Slave') and (./../../Protocol_SAIA_SBUS/RR_ComProt_SAIA_SBUS_SlaveDst = 'LASTRCV')) or ((./../../Protocol_SAIA_SBUS/RR_ComProt_SAIA_SBUS_Mode = 'SlavePlus') and (./../../Protocol_SAIA_SBUS/RR_ComProt_SAIA_SBUS_SlaveDst = 'LASTRCV')))";
                                type "lbox_udp_reserved_ports";
                            }
                            leaf "RR_ComProt_SAIA_SBUS_AtrmUdpPortSlave" {
                                when "not (./../../Protocol_SAIA_SBUS/RR_ComProt_SAIA_SBUS_DstStdPortSlave != 'MANUAL')";
                                type "lim_udp_port";
                            }
                        }
                        list "RR_S_TABLE_Protocol_SAIA_SBUS_TTable" {
                            when "not ((./../Protocol_SAIA_SBUS/RR_ComProt_SAIA_SBUS_AtrMethod = 'Mask') or (./../Protocol_SAIA_SBUS/RR_ComProt_SAIA_SBUS_Mode = 'Slave'))";
                            key "ID";
                            max-elements "1024";
                            ordered-by "user";
                            leaf "ID" {
                                type "lim_uint_16";
                            }
                            leaf "TTEntry_SAIA_SBUS_Ena" {
                                type "lbox_off_on";
                                default "On";
                            }
                            leaf "TTEntry_SAIA_SBUS_Note" {
                                type "string" {
                                    pattern "[^\"`\\\\$;]{0,42}";
                                }
                                default "";
                            }
                            leaf "TTEntry_SAIA_SBUS_DevAddr_1B" {
                                type "lim_uint_8";
                                must ". <= ../TTEntry_SAIA_SBUS_DevAddrLast_1B" {
                                    error-message "valmsg_it_TTEntry_SAIA_SBUS_DevAddr_1B";
                                }
                                default "1";
                            }
                            leaf "TTEntry_SAIA_SBUS_DevAddrLast_1B" {
                                type "lim_uint_8";
                                must ". >= ../TTEntry_SAIA_SBUS_DevAddr_1B" {
                                    error-message "valmsg_it_TTEntry_SAIA_SBUS_DevAddr_1B";
                                }
                                default "1";
                            }
                            leaf "TTEntry_SAIA_SBUS_IpAddr" {
                                type "inet:ipv4-address";
                                default "0.0.0.0";
                            }
                            leaf "TTEntry_SAIA_SBUS_IpInt" {
                                type "lbox_off_on";
                                default "Off";
                            }
                            leaf "TTEntry_SAIA_SBUS_StdPort" {
                                type "lbox_udp_reserved_ports";
                                default "COM1";
                            }
                            leaf "TTEntry_SAIA_SBUS_ManPort" {
                                when "not (../TTEntry_SAIA_SBUS_StdPort != 'MANUAL')";
                                type "lim_udp_port";
                                default "50000";
                            }
                        }
                    }
                }
                case "c-Mars-A" {
                    when "deref(./_variant_source_ref) = \"Mars-A\"";
                    container "Mars-A" {
                        container "Protocol_MarsA" {
                            leaf "RR_ComProt_MarsA_AtrmIpBase" {
                                when "not (./../../Protocol_MarsA/RR_ComProt_MarsA_AtrMethod = 'Table')";
                                type "inet:ipv4-address";
                            }
                            leaf "RR_ComProt_MarsA_AtrmUdpPort" {
                                when "not ((./../../Protocol_MarsA/RR_ComProt_MarsA_AtrMethod = 'Table') or (./../../Protocol_MarsA/RR_ComProt_MarsA_DstStdPort != 'MANUAL'))";
                                type "lim_udp_port";
                            }
                            leaf "RR_ComProt_MarsA_Repeats" {
                                type "uint8" {
                                    range "0..31";
                                }
                            }
                            leaf "RR_ComProt_MarsA_Bcast" {
                                when "not (/config_data/device/DeviceHw/RR_DynHw_Primary_Radio != 'On')";
                                type "lbox_off_on";
                            }
                            leaf "RR_ComProt_MarsA_Crc" {
                                type "lbox_off_on";
                            }
                            leaf "RR_ComProt_MarsA_AtrMethod" {
                                type "lbox_com_prot_addr_mode";
                            }
                            leaf "RR_ComProt_MarsA_AtrmIpMask" {
                                when "not (./../../Protocol_MarsA/RR_ComProt_MarsA_AtrMethod = 'Table')";
                                type "lim_ipv4_mask";
                            }
                            leaf "RR_ComProt_MarsA_SecurityBit" {
                                type "lbox_off_on";
                            }
                            leaf "RR_ComProt_MarsA_DstStdPort" {
                                when "not (./../../Protocol_MarsA/RR_ComProt_MarsA_AtrMethod = 'Table')";
                                type "lbox_udp_reserved_ports";
                            }
                            leaf "RR_ComProt_MarsA_RepeatTimeout" {
                                type "uint16" {
                                    range "0..16383";
                                }
                            }
                        }
                        list "RR_S_TABLE_Protocol_MarsA_TTable" {
                            when "not (./../Protocol_MarsA/RR_ComProt_MarsA_AtrMethod = 'Mask')";
                            key "ID";
                            max-elements "1024";
                            ordered-by "user";
                            leaf "ID" {
                                type "lim_uint_16";
                            }
                            leaf "TTEntry_MarsA_Ena" {
                                type "lbox_off_on";
                                default "On";
                            }
                            leaf "TTEntry_MarsA_Note" {
                                type "string" {
                                    pattern "[^\"`\\\\$;]{0,42}";
                                }
                                default "";
                            }
                            leaf "TTEntry_MarsA_DevAddr_4B" {
                                type "lim_uint_32";
                                must ". <= ../TTEntry_MarsA_DevAddrLast_4B" {
                                    error-message "valmsg_it_TTEntry_MarsA_DevAddr_4B";
                                }
                                default "1";
                            }
                            leaf "TTEntry_MarsA_DevAddrLast_4B" {
                                type "lim_uint_32";
                                must ". >= ../TTEntry_MarsA_DevAddr_4B" {
                                    error-message "valmsg_it_TTEntry_MarsA_DevAddr_4B";
                                }
                                default "1";
                            }
                            leaf "TTEntry_MarsA_IpAddr" {
                                type "inet:ipv4-address";
                                default "0.0.0.0";
                            }
                            leaf "TTEntry_MarsA_IpInt" {
                                type "lbox_off_on";
                                default "Off";
                            }
                            leaf "TTEntry_MarsA_StdPort" {
                                type "lbox_udp_reserved_ports";
                                default "COM1";
                            }
                            leaf "TTEntry_MarsA_ManPort" {
                                when "not (../TTEntry_MarsA_StdPort != 'MANUAL')";
                                type "lim_udp_port";
                                default "50000";
                            }
                        }
                    }
                }
                case "c-COMLI" {
                    when "deref(./_variant_source_ref) = \"COMLI\"";
                    container "COMLI" {
                        container "Protocol_COMLI" {
                            leaf "RR_ComProt_COMLI_AtrmIpBase" {
                                when "not ((./../../Protocol_COMLI/RR_ComProt_COMLI_AtrMethod = 'Table') or (./../../Protocol_COMLI/RR_ComProt_COMLI_Mode = 'Slave'))";
                                type "inet:ipv4-address";
                            }
                            leaf "RR_ComProt_COMLI_AtrmUdpPort" {
                                when "not ((./../../Protocol_COMLI/RR_ComProt_COMLI_AtrMethod = 'Table') or (./../../Protocol_COMLI/RR_ComProt_COMLI_DstStdPort != 'MANUAL'))";
                                type "lim_udp_port";
                            }
                            leaf "RR_ComProt_COMLI_Mode" {
                                type "lbox_com_prot_mode";
                            }
                            leaf "RR_ComProt_COMLI_AtrMethod" {
                                when "not (./../../Protocol_COMLI/RR_ComProt_COMLI_Mode = 'Slave')";
                                type "lbox_com_prot_addr_mode";
                            }
                            leaf "RR_ComProt_COMLI_AtrmIpMask" {
                                when "not ((./../../Protocol_COMLI/RR_ComProt_COMLI_Mode = 'Slave') or (./../../Protocol_COMLI/RR_ComProt_COMLI_AtrMethod = 'Table'))";
                                type "lim_ipv4_mask";
                            }
                            leaf "RR_ComProt_COMLI_DstStdPort" {
                                when "not (((./../../Protocol_COMLI/RR_ComProt_COMLI_Mode = 'Master') and (./../../Protocol_COMLI/RR_ComProt_COMLI_AtrMethod = 'Table')) or ((./../../Protocol_COMLI/RR_ComProt_COMLI_Mode = 'Slave') and (./../../Protocol_COMLI/RR_ComProt_COMLI_SlaveDst = 'LASTRCV')))";
                                type "lbox_udp_reserved_ports";
                            }
                            leaf "RR_ComProt_COMLI_SlaveDst" {
                                when "not (./../../Protocol_COMLI/RR_ComProt_COMLI_Mode != 'Slave')";
                                type "lbox_com_prot_slave_dst";
                            }
                            leaf "RR_ComProt_COMLI_ResponseTimeout" {
                                when "not (./../../Protocol_COMLI/RR_ComProt_COMLI_Mode != 'Slave')";
                                type "uint16" {
                                    range "0..16383";
                                }
                            }
                            leaf "RR_ComProt_COMLI_CongestionTimeout" {
                                when "not (./../../Protocol_COMLI/RR_ComProt_COMLI_Mode != 'Master')";
                                type "uint16" {
                                    range "0..65535";
                                }
                            }
                            leaf "RR_ComProt_COMLI_SlaveTargetIp" {
                                when "not ((./../../Protocol_COMLI/RR_ComProt_COMLI_Mode = 'Master') or ((./../../Protocol_COMLI/RR_ComProt_COMLI_Mode = 'Slave') and (./../../Protocol_COMLI/RR_ComProt_COMLI_SlaveDst = 'LASTRCV')))";
                                type "inet:ipv4-address";
                            }
                        }
                        list "RR_S_TABLE_Protocol_COMLI_TTable" {
                            when "not (./../Protocol_COMLI/RR_ComProt_COMLI_AtrMethod = 'Mask')";
                            key "ID";
                            max-elements "1024";
                            ordered-by "user";
                            leaf "ID" {
                                type "lim_uint_16";
                            }
                            leaf "TTEntry_COMLI_Ena" {
                                type "lbox_off_on";
                                default "On";
                            }
                            leaf "TTEntry_COMLI_Note" {
                                type "string" {
                                    pattern "[^\"`\\\\$;]{0,42}";
                                }
                                default "";
                            }
                            leaf "TTEntry_COMLI_DevAddr_1B" {
                                type "lim_uint_8";
                                must ". <= ../TTEntry_COMLI_DevAddrLast_1B" {
                                    error-message "valmsg_it_TTEntry_COMLI_DevAddr_1B";
                                }
                                default "1";
                            }
                            leaf "TTEntry_COMLI_DevAddrLast_1B" {
                                type "lim_uint_8";
                                must ". >= ../TTEntry_COMLI_DevAddr_1B" {
                                    error-message "valmsg_it_TTEntry_COMLI_DevAddr_1B";
                                }
                                default "1";
                            }
                            leaf "TTEntry_COMLI_IpAddr" {
                                type "inet:ipv4-address";
                                default "0.0.0.0";
                            }
                            leaf "TTEntry_COMLI_IpInt" {
                                type "lbox_off_on";
                                default "Off";
                            }
                            leaf "TTEntry_COMLI_StdPort" {
                                type "lbox_udp_reserved_ports";
                                default "COM1";
                            }
                            leaf "TTEntry_COMLI_ManPort" {
                                when "not (../TTEntry_COMLI_StdPort != 'MANUAL')";
                                type "lim_udp_port";
                                default "50000";
                            }
                        }
                    }
                }
            }
        }
        container "main" {
            container "Main" {
                leaf "RR_StationName" {
                    type "string" {
                        pattern "[a-zA-Z0-9_]{1,64}";
                    }
                }
                leaf "RR_StationDesc" {
                    type "string" {
                        pattern "[^\"`\\\\$;]{0,1024}";
                    }
                }
                leaf "RR_DevicePortBase" {
                    type "uint16" {
                        range "1024..64512";
                    }
                }
                leaf "RR_StationLocation" {
                    type "string" {
                        pattern "[ !#%-\\)\\+-:<-\\?@-\\[\\]-_a-~]{0,255}";
                    }
                }
                leaf "RR_StationContactInfo" {
                    type "string" {
                        pattern "[ !#%-\\)\\+-:<-\\?@-\\[\\]-_a-~]{0,255}";
                    }
                }
            }
            container "EthPorts" {
                leaf "RR_EthPort_1_Enable" {
                    when "not (/config_data/device/DeviceHw/RR_DynHw_Port_Eth_Cnt <= 0)";
                    type "lbox_off_on";
                }
                leaf "RR_EthPort_1_AutoNeg" {
                    when "not ((/config_data/device/DeviceHw/RR_DynHw_Port_Eth_Cnt <= 0) or (/config_data/main/EthPorts/RR_EthPort_1_Enable != 'On'))";
                    type "lbox_eth_autoneg_M1";
                    must "not ((. = 'LB_eth_autoneg_1000mbps_auto' and (/config_data/device/DeviceHw/RR_DynHw_Port_Eth_Speed <= 100)) or (. = 'LB_eth_autoneg_1000mbps_full' and ((/config_data/device/DeviceHw/RR_DynHw_Port_Eth_1000Mbps_Full != 'On') or (/config_data/device/DeviceHw/RR_DynHw_Port_Eth_Speed <= 100))) or (. = 'LB_eth_autoneg_1000mbps_half' and ((/config_data/device/DeviceHw/RR_DynHw_Port_Eth_1000Mbps_Half != 'On') or (/config_data/device/DeviceHw/RR_DynHw_Port_Eth_Speed <= 100))) or (. = 'LB_eth_autoneg_100mbps_auto' and (/config_data/device/DeviceHw/RR_DynHw_Port_Eth_Speed <= 10)) or (. = 'LB_eth_autoneg_100mbps_full' and (/config_data/device/DeviceHw/RR_DynHw_Port_Eth_Speed <= 10)) or (. = 'LB_eth_autoneg_100mbps_half' and (/config_data/device/DeviceHw/RR_DynHw_Port_Eth_Speed <= 10)))";
                }
                leaf "RR_EthPort_2_Enable" {
                    when "not (/config_data/device/DeviceHw/RR_DynHw_Port_Eth_Cnt <= 1)";
                    type "lbox_off_on";
                }
                leaf "RR_EthPort_2_AutoNeg" {
                    when "not ((/config_data/device/DeviceHw/RR_DynHw_Port_Eth_Cnt <= 1) or (/config_data/main/EthPorts/RR_EthPort_2_Enable != 'On'))";
                    type "lbox_eth_autoneg_M1";
                    must "not ((. = 'LB_eth_autoneg_1000mbps_auto' and (/config_data/device/DeviceHw/RR_DynHw_Port_Eth_Speed <= 100)) or (. = 'LB_eth_autoneg_1000mbps_full' and ((/config_data/device/DeviceHw/RR_DynHw_Port_Eth_1000Mbps_Full != 'On') or (/config_data/device/DeviceHw/RR_DynHw_Port_Eth_Speed <= 100))) or (. = 'LB_eth_autoneg_1000mbps_half' and ((/config_data/device/DeviceHw/RR_DynHw_Port_Eth_1000Mbps_Half != 'On') or (/config_data/device/DeviceHw/RR_DynHw_Port_Eth_Speed <= 100))) or (. = 'LB_eth_autoneg_100mbps_auto' and (/config_data/device/DeviceHw/RR_DynHw_Port_Eth_Speed <= 10)) or (. = 'LB_eth_autoneg_100mbps_full' and (/config_data/device/DeviceHw/RR_DynHw_Port_Eth_Speed <= 10)) or (. = 'LB_eth_autoneg_100mbps_half' and (/config_data/device/DeviceHw/RR_DynHw_Port_Eth_Speed <= 10)))";
                }
                leaf "RR_EthPort_3_Enable" {
                    when "not (/config_data/device/DeviceHw/RR_DynHw_Port_Eth_Cnt <= 2)";
                    type "lbox_off_on";
                }
                leaf "RR_EthPort_3_AutoNeg" {
                    when "not ((/config_data/device/DeviceHw/RR_DynHw_Port_Eth_Cnt <= 2) or (/config_data/main/EthPorts/RR_EthPort_3_Enable != 'On'))";
                    type "lbox_eth_autoneg_M1";
                    must "not ((. = 'LB_eth_autoneg_1000mbps_auto' and (/config_data/device/DeviceHw/RR_DynHw_Port_Eth_Speed <= 100)) or (. = 'LB_eth_autoneg_1000mbps_full' and ((/config_data/device/DeviceHw/RR_DynHw_Port_Eth_1000Mbps_Full != 'On') or (/config_data/device/DeviceHw/RR_DynHw_Port_Eth_Speed <= 100))) or (. = 'LB_eth_autoneg_1000mbps_half' and ((/config_data/device/DeviceHw/RR_DynHw_Port_Eth_1000Mbps_Half != 'On') or (/config_data/device/DeviceHw/RR_DynHw_Port_Eth_Speed <= 100))) or (. = 'LB_eth_autoneg_100mbps_auto' and (/config_data/device/DeviceHw/RR_DynHw_Port_Eth_Speed <= 10)) or (. = 'LB_eth_autoneg_100mbps_full' and (/config_data/device/DeviceHw/RR_DynHw_Port_Eth_Speed <= 10)) or (. = 'LB_eth_autoneg_100mbps_half' and (/config_data/device/DeviceHw/RR_DynHw_Port_Eth_Speed <= 10)))";
                }
                leaf "RR_EthPort_4_Enable" {
                    when "not (/config_data/device/DeviceHw/RR_DynHw_Port_Eth_Cnt <= 3)";
                    type "lbox_off_on";
                }
                leaf "RR_EthPort_4_AutoNeg" {
                    when "not ((/config_data/device/DeviceHw/RR_DynHw_Port_Eth_Cnt <= 3) or (/config_data/main/EthPorts/RR_EthPort_4_Enable != 'On'))";
                    type "lbox_eth_autoneg_M1";
                    must "not ((. = 'LB_eth_autoneg_1000mbps_auto' and (/config_data/device/DeviceHw/RR_DynHw_Port_Eth_Speed <= 100)) or (. = 'LB_eth_autoneg_1000mbps_full' and ((/config_data/device/DeviceHw/RR_DynHw_Port_Eth_1000Mbps_Full != 'On') or (/config_data/device/DeviceHw/RR_DynHw_Port_Eth_Speed <= 100))) or (. = 'LB_eth_autoneg_1000mbps_half' and ((/config_data/device/DeviceHw/RR_DynHw_Port_Eth_1000Mbps_Half != 'On') or (/config_data/device/DeviceHw/RR_DynHw_Port_Eth_Speed <= 100))) or (. = 'LB_eth_autoneg_100mbps_auto' and (/config_data/device/DeviceHw/RR_DynHw_Port_Eth_Speed <= 10)) or (. = 'LB_eth_autoneg_100mbps_full' and (/config_data/device/DeviceHw/RR_DynHw_Port_Eth_Speed <= 10)) or (. = 'LB_eth_autoneg_100mbps_half' and (/config_data/device/DeviceHw/RR_DynHw_Port_Eth_Speed <= 10)))";
                }
            }
            container "ExtensionPorts" {
                leaf "RR_PortSfpEnable" {
                    when "not (/config_data/device/DeviceHw/RR_DynHw_Port_Sfp != 'On')";
                    type "enumeration" {
                        enum "Off" {
                            value "0";
                        }
                        enum "On" {
                            value "1";
                        }
                    }
                    must "not ((. = 'On' and (/config_data/device/DeviceSwKey/RR_SwKey_Flag_interface_sfp != 'On')))";
                }
            }
            container "EventSysBootCompleted" {
                leaf "RR_Event_Sys_Boot_Completed_Sev" {
                    type "lbox_event_severity";
                }
                leaf "RR_Event_Sys_Boot_Completed_AO" {
                    type "lbox_off_on";
                }
                leaf "RR_Event_Sys_Boot_Completed_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Sys_Boot_Completed_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Sys_Boot_Completed_Snmp" {
                    when "not ((/config_data/main/SNMP/RR_SnmpNotification = 'Off') or (/config_data/main/SNMP/RR_SnmpMode = 'Off'))";
                    type "lbox_off_on";
                }
                leaf "RR_Event_Sys_Boot_Completed_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventSysRecoveryMode" {
                leaf "RR_Event_Sys_Recovery_Mode_Sev" {
                    type "enumeration" {
                        enum "Emergency" {
                            value "0";
                        }
                        enum "Alert" {
                            value "1";
                        }
                        enum "Critical" {
                            value "2";
                        }
                        enum "Error" {
                            value "3";
                        }
                        enum "Warning" {
                            value "4";
                        }
                        enum "Notice" {
                            value "5";
                        }
                        enum "Informational" {
                            value "6";
                        }
                        enum "Debug" {
                            value "7";
                        }
                    }
                    must "not ((. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)) or (. = 'Warning' and (/config_data/auth/CnfAuth/RR_CnfAuthCnfVersion >= 0)) or (. = 'Notice' and (/config_data/auth/CnfAuth/RR_CnfAuthCnfVersion >= 0)) or (. = 'Informational' and (/config_data/auth/CnfAuth/RR_CnfAuthCnfVersion >= 0)) or (. = 'Debug' and (/config_data/auth/CnfAuth/RR_CnfAuthCnfVersion >= 0)))";
                }
            }
            container "EventSysRecoveryRestart" {
                leaf "RR_Event_Sys_Recovery_Restart_Sev" {
                    type "enumeration" {
                        enum "Emergency" {
                            value "0";
                        }
                        enum "Alert" {
                            value "1";
                        }
                        enum "Critical" {
                            value "2";
                        }
                        enum "Error" {
                            value "3";
                        }
                        enum "Warning" {
                            value "4";
                        }
                        enum "Notice" {
                            value "5";
                        }
                        enum "Informational" {
                            value "6";
                        }
                        enum "Debug" {
                            value "7";
                        }
                    }
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)) or (. = 'Notice' and (/config_data/auth/CnfAuth/RR_CnfAuthCnfVersion >= 0)) or (. = 'Informational' and (/config_data/auth/CnfAuth/RR_CnfAuthCnfVersion >= 0)) or (. = 'Debug' and (/config_data/auth/CnfAuth/RR_CnfAuthCnfVersion >= 0)))";
                }
            }
            container "EventSysCnfLost" {
                leaf "RR_Event_Sys_Cnf_Lost_Sev" {
                    type "enumeration" {
                        enum "Emergency" {
                            value "0";
                        }
                        enum "Alert" {
                            value "1";
                        }
                        enum "Critical" {
                            value "2";
                        }
                        enum "Error" {
                            value "3";
                        }
                        enum "Warning" {
                            value "4";
                        }
                        enum "Notice" {
                            value "5";
                        }
                        enum "Informational" {
                            value "6";
                        }
                        enum "Debug" {
                            value "7";
                        }
                    }
                    must "not ((. = 'Emergency' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)) or (. = 'Warning' and (/config_data/auth/CnfAuth/RR_CnfAuthCnfVersion >= 0)) or (. = 'Notice' and (/config_data/auth/CnfAuth/RR_CnfAuthCnfVersion >= 0)) or (. = 'Informational' and (/config_data/auth/CnfAuth/RR_CnfAuthCnfVersion >= 0)) or (. = 'Debug' and (/config_data/auth/CnfAuth/RR_CnfAuthCnfVersion >= 0)))";
                }
            }
            container "EventSysPurged" {
                leaf "RR_Event_Sys_Purged_Sev" {
                    type "enumeration" {
                        enum "Emergency" {
                            value "0";
                        }
                        enum "Alert" {
                            value "1";
                        }
                        enum "Critical" {
                            value "2";
                        }
                        enum "Error" {
                            value "3";
                        }
                        enum "Warning" {
                            value "4";
                        }
                        enum "Notice" {
                            value "5";
                        }
                        enum "Informational" {
                            value "6";
                        }
                        enum "Debug" {
                            value "7";
                        }
                    }
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)) or (. = 'Warning' and (/config_data/auth/CnfAuth/RR_CnfAuthCnfVersion >= 0)) or (. = 'Informational' and (/config_data/auth/CnfAuth/RR_CnfAuthCnfVersion >= 0)) or (. = 'Debug' and (/config_data/auth/CnfAuth/RR_CnfAuthCnfVersion >= 0)))";
                }
            }
            container "EventSysFactorySet" {
                leaf "RR_Event_Sys_Factory_Set_Sev" {
                    type "enumeration" {
                        enum "Emergency" {
                            value "0";
                        }
                        enum "Alert" {
                            value "1";
                        }
                        enum "Critical" {
                            value "2";
                        }
                        enum "Error" {
                            value "3";
                        }
                        enum "Warning" {
                            value "4";
                        }
                        enum "Notice" {
                            value "5";
                        }
                        enum "Informational" {
                            value "6";
                        }
                        enum "Debug" {
                            value "7";
                        }
                    }
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)) or (. = 'Warning' and (/config_data/auth/CnfAuth/RR_CnfAuthCnfVersion >= 0)) or (. = 'Informational' and (/config_data/auth/CnfAuth/RR_CnfAuthCnfVersion >= 0)) or (. = 'Debug' and (/config_data/auth/CnfAuth/RR_CnfAuthCnfVersion >= 0)))";
                }
            }
            container "EventSysDataFormat" {
                leaf "RR_Event_Sys_Data_Format_Sev" {
                    type "enumeration" {
                        enum "Emergency" {
                            value "0";
                        }
                        enum "Alert" {
                            value "1";
                        }
                        enum "Critical" {
                            value "2";
                        }
                        enum "Error" {
                            value "3";
                        }
                        enum "Warning" {
                            value "4";
                        }
                        enum "Notice" {
                            value "5";
                        }
                        enum "Informational" {
                            value "6";
                        }
                        enum "Debug" {
                            value "7";
                        }
                    }
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)) or (. = 'Warning' and (/config_data/auth/CnfAuth/RR_CnfAuthCnfVersion >= 0)) or (. = 'Informational' and (/config_data/auth/CnfAuth/RR_CnfAuthCnfVersion >= 0)) or (. = 'Debug' and (/config_data/auth/CnfAuth/RR_CnfAuthCnfVersion >= 0)))";
                }
            }
            container "EventSysCnfUpdate" {
                leaf "RR_Event_Sys_Cnf_Update_Sev" {
                    type "lbox_event_severity";
                }
                leaf "RR_Event_Sys_Cnf_Update_Snmp" {
                    when "not ((/config_data/main/SNMP/RR_SnmpNotification = 'Off') or (/config_data/main/SNMP/RR_SnmpMode = 'Off'))";
                    type "lbox_off_on";
                }
                leaf "RR_Event_Sys_Cnf_Update_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventSysReboot" {
                leaf "RR_Event_Sys_Reboot_Sev" {
                    type "lbox_event_severity";
                }
            }
            container "EventSysFwUpgrade" {
                leaf "RR_Event_Sys_FW_Upgrade_Sev" {
                    type "lbox_event_severity";
                }
                leaf "RR_Event_Sys_FW_Upgrade_Snmp" {
                    when "not ((/config_data/main/SNMP/RR_SnmpNotification = 'Off') or (/config_data/main/SNMP/RR_SnmpMode = 'Off'))";
                    type "lbox_off_on";
                }
            }
            container "EventUsbFlashDisc" {
                leaf "RR_Event_Usb_Flash_Disc_Sev" {
                    type "lbox_event_severity";
                }
                leaf "RR_Event_Usb_Flash_Disc_AO" {
                    type "lbox_off_on";
                }
                leaf "RR_Event_Usb_Flash_Disc_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Usb_Flash_Disc_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Usb_Flash_Disc_Snmp" {
                    when "not ((/config_data/main/SNMP/RR_SnmpNotification = 'Off') or (/config_data/main/SNMP/RR_SnmpMode = 'Off'))";
                    type "lbox_off_on";
                }
                leaf "RR_Event_Usb_Flash_Disc_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventUsbOvercurrent" {
                leaf "RR_Event_USB_Overcurrent_Sev" {
                    type "lbox_event_severity";
                }
                leaf "RR_Event_USB_Overcurrent_AO" {
                    type "lbox_off_on";
                }
                leaf "RR_Event_USB_Overcurrent_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_USB_Overcurrent_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_USB_Overcurrent_Snmp" {
                    when "not ((/config_data/main/SNMP/RR_SnmpNotification = 'Off') or (/config_data/main/SNMP/RR_SnmpMode = 'Off'))";
                    type "lbox_off_on";
                }
                leaf "RR_Event_USB_Overcurrent_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventRtcBatteryLow" {
                leaf "RR_Event_RTC_Battery_Low_Sev" {
                    type "lbox_event_severity";
                }
                leaf "RR_Event_RTC_Battery_Low_AO" {
                    type "lbox_off_on";
                }
                leaf "RR_Event_RTC_Battery_Low_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_RTC_Battery_Low_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_RTC_Battery_Low_Snmp" {
                    when "not ((/config_data/main/SNMP/RR_SnmpNotification = 'Off') or (/config_data/main/SNMP/RR_SnmpMode = 'Off'))";
                    type "lbox_off_on";
                }
                leaf "RR_Event_RTC_Battery_Low_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventSfpOvercurrent" {
                when "not ((/config_data/device/DeviceHw/RR_DynHw_Port_Sfp != 'On') or (/config_data/main/ExtensionPorts/RR_PortSfpEnable != 'On'))";
                leaf "RR_Event_SFP_Overcurent_Sev" {
                    type "lbox_event_severity";
                }
                leaf "RR_Event_SFP_Overcurent_AO" {
                    type "lbox_off_on";
                }
                leaf "RR_Event_SFP_Overcurent_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_SFP_Overcurent_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_SFP_Overcurent_Snmp" {
                    when "not ((/config_data/main/SNMP/RR_SnmpNotification = 'Off') or (/config_data/main/SNMP/RR_SnmpMode = 'Off'))";
                    type "lbox_off_on";
                }
                leaf "RR_Event_SFP_Overcurent_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventSfpFault" {
                when "not ((/config_data/device/DeviceHw/RR_DynHw_Port_Sfp != 'On') or (/config_data/main/ExtensionPorts/RR_PortSfpEnable != 'On'))";
                leaf "RR_Event_SFP_Fault_Sev" {
                    type "lbox_event_severity";
                }
                leaf "RR_Event_SFP_Fault_AO" {
                    type "lbox_off_on";
                }
                leaf "RR_Event_SFP_Fault_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_SFP_Fault_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_SFP_Fault_Snmp" {
                    when "not ((/config_data/main/SNMP/RR_SnmpNotification = 'Off') or (/config_data/main/SNMP/RR_SnmpMode = 'Off'))";
                    type "lbox_off_on";
                }
                leaf "RR_Event_SFP_Fault_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventSfpNotPresent" {
                when "not ((/config_data/device/DeviceHw/RR_DynHw_Port_Sfp != 'On') or (/config_data/main/ExtensionPorts/RR_PortSfpEnable != 'On'))";
                leaf "RR_Event_SFP_Not_Present_Sev" {
                    type "lbox_event_severity";
                }
                leaf "RR_Event_SFP_Not_Present_AO" {
                    type "lbox_off_on";
                }
                leaf "RR_Event_SFP_Not_Present_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_SFP_Not_Present_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_SFP_Not_Present_Snmp" {
                    when "not ((/config_data/main/SNMP/RR_SnmpNotification = 'Off') or (/config_data/main/SNMP/RR_SnmpMode = 'Off'))";
                    type "lbox_off_on";
                }
                leaf "RR_Event_SFP_Not_Present_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventEth1LinkDown" {
                when "not ((/config_data/device/DeviceHw/RR_DynHw_Port_Eth_Cnt <= 0) or (/config_data/main/EthPorts/RR_EthPort_1_Enable != 'On'))";
                leaf "RR_Event_ETH1_Link_Down_Sev" {
                    type "lbox_event_severity";
                }
                leaf "RR_Event_ETH1_Link_Down_AO" {
                    type "lbox_off_on";
                }
                leaf "RR_Event_ETH1_Link_Down_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_ETH1_Link_Down_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_ETH1_Link_Down_Snmp" {
                    when "not ((/config_data/main/SNMP/RR_SnmpNotification = 'Off') or (/config_data/main/SNMP/RR_SnmpMode = 'Off'))";
                    type "lbox_off_on";
                }
                leaf "RR_Event_ETH1_Link_Down_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_ETH1_Link_Down_HS" {
                    when "not ((/config_data/device/DeviceHw/RR_DynHw_HotStandby != 'On') or (/config_data/main/HotStdby/RR_HotStdby_Enable != 'On'))";
                    type "lbox_off_on";
                }
            }
            container "EventEth2LinkDown" {
                when "not ((/config_data/device/DeviceHw/RR_DynHw_Port_Eth_Cnt <= 1) or (/config_data/main/EthPorts/RR_EthPort_2_Enable != 'On'))";
                leaf "RR_Event_ETH2_Link_Down_Sev" {
                    type "lbox_event_severity";
                }
                leaf "RR_Event_ETH2_Link_Down_AO" {
                    type "lbox_off_on";
                }
                leaf "RR_Event_ETH2_Link_Down_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_ETH2_Link_Down_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_ETH2_Link_Down_Snmp" {
                    when "not ((/config_data/main/SNMP/RR_SnmpNotification = 'Off') or (/config_data/main/SNMP/RR_SnmpMode = 'Off'))";
                    type "lbox_off_on";
                }
                leaf "RR_Event_ETH2_Link_Down_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_ETH2_Link_Down_HS" {
                    when "not ((/config_data/device/DeviceHw/RR_DynHw_HotStandby != 'On') or (/config_data/main/HotStdby/RR_HotStdby_Enable != 'On'))";
                    type "lbox_off_on";
                }
            }
            container "EventEth3LinkDown" {
                when "not ((/config_data/device/DeviceHw/RR_DynHw_Port_Eth_Cnt <= 2) or (/config_data/main/EthPorts/RR_EthPort_3_Enable != 'On'))";
                leaf "RR_Event_ETH3_Link_Down_Sev" {
                    type "lbox_event_severity";
                }
                leaf "RR_Event_ETH3_Link_Down_AO" {
                    type "lbox_off_on";
                }
                leaf "RR_Event_ETH3_Link_Down_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_ETH3_Link_Down_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_ETH3_Link_Down_Snmp" {
                    when "not ((/config_data/main/SNMP/RR_SnmpNotification = 'Off') or (/config_data/main/SNMP/RR_SnmpMode = 'Off'))";
                    type "lbox_off_on";
                }
                leaf "RR_Event_ETH3_Link_Down_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_ETH3_Link_Down_HS" {
                    when "not ((/config_data/device/DeviceHw/RR_DynHw_HotStandby != 'On') or (/config_data/main/HotStdby/RR_HotStdby_Enable != 'On'))";
                    type "lbox_off_on";
                }
            }
            container "EventEth4LinkDown" {
                when "not ((/config_data/device/DeviceHw/RR_DynHw_Port_Eth_Cnt <= 3) or (/config_data/main/EthPorts/RR_EthPort_4_Enable != 'On'))";
                leaf "RR_Event_ETH4_Link_Down_Sev" {
                    type "lbox_event_severity";
                }
                leaf "RR_Event_ETH4_Link_Down_AO" {
                    type "lbox_off_on";
                }
                leaf "RR_Event_ETH4_Link_Down_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_ETH4_Link_Down_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_ETH4_Link_Down_Snmp" {
                    when "not ((/config_data/main/SNMP/RR_SnmpNotification = 'Off') or (/config_data/main/SNMP/RR_SnmpMode = 'Off'))";
                    type "lbox_off_on";
                }
                leaf "RR_Event_ETH4_Link_Down_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_ETH4_Link_Down_HS" {
                    when "not ((/config_data/device/DeviceHw/RR_DynHw_HotStandby != 'On') or (/config_data/main/HotStdby/RR_HotStdby_Enable != 'On'))";
                    type "lbox_off_on";
                }
            }
            container "EventEth5LinkDown" {
                when "not ((/config_data/device/DeviceHw/RR_DynHw_Port_Sfp != 'On') or (/config_data/main/ExtensionPorts/RR_PortSfpEnable != 'On'))";
                leaf "RR_Event_ETH5_Link_Down_Sev" {
                    type "lbox_event_severity";
                }
                leaf "RR_Event_ETH5_Link_Down_AO" {
                    type "lbox_off_on";
                }
                leaf "RR_Event_ETH5_Link_Down_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_ETH5_Link_Down_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_ETH5_Link_Down_Snmp" {
                    when "not ((/config_data/main/SNMP/RR_SnmpNotification = 'Off') or (/config_data/main/SNMP/RR_SnmpMode = 'Off'))";
                    type "lbox_off_on";
                }
                leaf "RR_Event_ETH5_Link_Down_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_ETH5_Link_Down_HS" {
                    when "not ((/config_data/device/DeviceHw/RR_DynHw_HotStandby != 'On') or (/config_data/main/HotStdby/RR_HotStdby_Enable != 'On'))";
                    type "lbox_off_on";
                }
            }
            container "EventMoniCongestion" {
                leaf "RR_Event_Moni_Congestion_Sev" {
                    type "lbox_event_severity";
                }
                leaf "RR_Event_Moni_Congestion_AO" {
                    type "lbox_off_on";
                }
                leaf "RR_Event_Moni_Congestion_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Moni_Congestion_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Moni_Congestion_Snmp" {
                    when "not ((/config_data/main/SNMP/RR_SnmpNotification = 'Off') or (/config_data/main/SNMP/RR_SnmpMode = 'Off'))";
                    type "lbox_off_on";
                }
                leaf "RR_Event_Moni_Congestion_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventSvcAccess" {
                leaf "RR_Event_SVC_Access_Sev" {
                    type "lbox_event_severity";
                }
                leaf "RR_Event_SVC_Access_AO" {
                    type "lbox_off_on";
                }
                leaf "RR_Event_SVC_Access_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_SVC_Access_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_SVC_Access_Snmp" {
                    when "not ((/config_data/main/SNMP/RR_SnmpNotification = 'Off') or (/config_data/main/SNMP/RR_SnmpMode = 'Off'))";
                    type "lbox_off_on";
                }
                leaf "RR_Event_SVC_Access_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventWebAccessLogin" {
                leaf "RR_Event_Web_Access_Login_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_Web_Access_Login_Snmp" {
                    when "not ((/config_data/main/SNMP/RR_SnmpNotification = 'Off') or (/config_data/main/SNMP/RR_SnmpMode = 'Off'))";
                    type "lbox_off_on";
                }
            }
            container "EventWebAccessLoginFail" {
                leaf "RR_Event_Web_Access_Login_Fail_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_Web_Access_Login_Fail_Snmp" {
                    when "not ((/config_data/main/SNMP/RR_SnmpNotification = 'Off') or (/config_data/main/SNMP/RR_SnmpMode = 'Off'))";
                    type "lbox_off_on";
                }
            }
            container "EventWebAccessLoginFailAuthConn" {
                when "not (/config_data/main/UserAccess/RR_UsAcc_RadiusAuth = 'Off')";
                leaf "RR_Event_Web_Access_Login_Fail_AuthConn_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_Web_Access_Login_Fail_AuthConn_Snmp" {
                    when "not ((/config_data/main/SNMP/RR_SnmpNotification = 'Off') or (/config_data/main/SNMP/RR_SnmpMode = 'Off'))";
                    type "lbox_off_on";
                }
            }
            container "EventWebAccessLoginFailAuthReply" {
                when "not (/config_data/main/UserAccess/RR_UsAcc_RadiusAuth = 'Off')";
                leaf "RR_Event_Web_Access_Login_Fail_AuthReply_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_Web_Access_Login_Fail_AuthReply_Snmp" {
                    when "not ((/config_data/main/SNMP/RR_SnmpNotification = 'Off') or (/config_data/main/SNMP/RR_SnmpMode = 'Off'))";
                    type "lbox_off_on";
                }
            }
            container "EventAccessPasswordChanged" {
                leaf "RR_Event_Access_Password_Changed_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_Access_Password_Changed_Snmp" {
                    when "not ((/config_data/main/SNMP/RR_SnmpNotification = 'Off') or (/config_data/main/SNMP/RR_SnmpMode = 'Off'))";
                    type "lbox_off_on";
                }
            }
            container "EventAccessUserCreate" {
                leaf "RR_Event_Access_User_Create_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_Access_User_Create_Snmp" {
                    when "not ((/config_data/main/SNMP/RR_SnmpNotification = 'Off') or (/config_data/main/SNMP/RR_SnmpMode = 'Off'))";
                    type "lbox_off_on";
                }
            }
            container "EventAccessUserDelete" {
                leaf "RR_Event_Access_User_Delete_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_Access_User_Delete_Snmp" {
                    when "not ((/config_data/main/SNMP/RR_SnmpNotification = 'Off') or (/config_data/main/SNMP/RR_SnmpMode = 'Off'))";
                    type "lbox_off_on";
                }
            }
            container "EventAccessUserUpdate" {
                leaf "RR_Event_Access_User_Update_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_Access_User_Update_Snmp" {
                    when "not ((/config_data/main/SNMP/RR_SnmpNotification = 'Off') or (/config_data/main/SNMP/RR_SnmpMode = 'Off'))";
                    type "lbox_off_on";
                }
            }
            container "EventAccessUsersRestore" {
                leaf "RR_Event_Access_Users_Restore_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_Access_Users_Restore_Snmp" {
                    when "not ((/config_data/main/SNMP/RR_SnmpNotification = 'Off') or (/config_data/main/SNMP/RR_SnmpMode = 'Off'))";
                    type "lbox_off_on";
                }
            }
            container "EventRadioSerialMismatch" {
                when "not (/config_data/device/DeviceHw/RR_DynHw_Primary_Radio != 'On')";
                leaf "RR_Event_Radio_Serial_Mismatch_Sev" {
                    type "lbox_event_severity";
                }
            }
            container "EventRadioKeyingStart" {
                when "not (/config_data/device/DeviceHw/RR_DynHw_Primary_Radio != 'On')";
                leaf "RR_Event_Radio_Keying_Start_Sev" {
                    type "lbox_event_severity";
                }
                leaf "RR_Event_Radio_Keying_Start_Snmp" {
                    when "not ((/config_data/main/SNMP/RR_SnmpNotification = 'Off') or (/config_data/main/SNMP/RR_SnmpMode = 'Off'))";
                    type "lbox_off_on";
                }
            }
            container "EventRadioTxAntennaProblem" {
                when "not ((/config_data/device/DeviceHw/RR_DynHw_Primary_Radio != 'On') or (/config_data/device/DeviceHw/RR_DynHw_Radio_AntennaDet != 'On'))";
                leaf "RR_Event_Radio_Tx_Antenna_Problem_Sev" {
                    type "lbox_event_severity";
                }
                leaf "RR_Event_Radio_Tx_Antenna_Problem_AO" {
                    type "lbox_off_on";
                }
                leaf "RR_Event_Radio_Tx_Antenna_Problem_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Radio_Tx_Antenna_Problem_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Radio_Tx_Antenna_Problem_Snmp" {
                    when "not ((/config_data/main/SNMP/RR_SnmpNotification = 'Off') or (/config_data/main/SNMP/RR_SnmpMode = 'Off'))";
                    type "lbox_off_on";
                }
                leaf "RR_Event_Radio_Tx_Antenna_Problem_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_Radio_Tx_Antenna_Problem_HS" {
                    when "not ((/config_data/device/DeviceHw/RR_DynHw_HotStandby != 'On') or (/config_data/main/HotStdby/RR_HotStdby_Enable != 'On'))";
                    type "lbox_off_on";
                }
            }
            container "EventRadioTempLow" {
                when "not (/config_data/device/DeviceHw/RR_DynHw_Primary_Radio != 'On')";
                leaf "RR_Event_Radio_Temp_Low_Limit" {
                    type "int8" {
                        range "-40..20";
                    }
                }
                leaf "RR_Event_Radio_Temp_Low_Sev" {
                    type "lbox_event_severity";
                }
                leaf "RR_Event_Radio_Temp_Low_AO" {
                    type "lbox_off_on";
                }
                leaf "RR_Event_Radio_Temp_Low_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Radio_Temp_Low_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Radio_Temp_Low_Snmp" {
                    when "not ((/config_data/main/SNMP/RR_SnmpNotification = 'Off') or (/config_data/main/SNMP/RR_SnmpMode = 'Off'))";
                    type "lbox_off_on";
                }
                leaf "RR_Event_Radio_Temp_Low_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_Radio_Temp_Low_HS" {
                    when "not ((/config_data/device/DeviceHw/RR_DynHw_HotStandby != 'On') or (/config_data/main/HotStdby/RR_HotStdby_Enable != 'On'))";
                    type "lbox_off_on";
                }
                leaf "RR_Event_Radio_Temp_Low_Hyst" {
                    type "uint8" {
                        range "1..10";
                    }
                }
            }
            container "EventRadioTempHigh" {
                when "not (/config_data/device/DeviceHw/RR_DynHw_Primary_Radio != 'On')";
                leaf "RR_Event_Radio_Temp_High_Limit" {
                    type "uint8" {
                        range "40..85";
                    }
                }
                leaf "RR_Event_Radio_Temp_High_Sev" {
                    type "lbox_event_severity";
                }
                leaf "RR_Event_Radio_Temp_High_AO" {
                    type "lbox_off_on";
                }
                leaf "RR_Event_Radio_Temp_High_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Radio_Temp_High_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Radio_Temp_High_Snmp" {
                    when "not ((/config_data/main/SNMP/RR_SnmpNotification = 'Off') or (/config_data/main/SNMP/RR_SnmpMode = 'Off'))";
                    type "lbox_off_on";
                }
                leaf "RR_Event_Radio_Temp_High_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_Radio_Temp_High_HS" {
                    when "not ((/config_data/device/DeviceHw/RR_DynHw_HotStandby != 'On') or (/config_data/main/HotStdby/RR_HotStdby_Enable != 'On'))";
                    type "lbox_off_on";
                }
                leaf "RR_Event_Radio_Temp_High_Hyst" {
                    type "lim_Event_Radio_Temp_Low_Hyst_M2";
                }
            }
            container "EventRadioIntFault" {
                when "not (/config_data/device/DeviceHw/RR_DynHw_Primary_Radio != 'On')";
                leaf "RR_Event_Radio_IntFault_Sev" {
                    type "lbox_event_severity";
                }
                leaf "RR_Event_Radio_IntFault_AO" {
                    type "lbox_off_on";
                }
                leaf "RR_Event_Radio_IntFault_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Radio_IntFault_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Radio_IntFault_Snmp" {
                    when "not ((/config_data/main/SNMP/RR_SnmpNotification = 'Off') or (/config_data/main/SNMP/RR_SnmpMode = 'Off'))";
                    type "lbox_off_on";
                }
                leaf "RR_Event_Radio_IntFault_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_Radio_IntFault_HS" {
                    when "not ((/config_data/device/DeviceHw/RR_DynHw_HotStandby != 'On') or (/config_data/main/HotStdby/RR_HotStdby_Enable != 'On'))";
                    type "lbox_off_on";
                }
            }
            container "EventRadioBlockedCritTemp" {
                when "not ((/config_data/device/DeviceHw/RR_DynHw_Primary_Radio != 'On') or (/config_data/main/RadioChannel/RR_RadioTempTxBreaker != 'On'))";
                leaf "RR_Event_Radio_Blocked_CritTemp_Sev" {
                    type "enumeration" {
                        enum "Emergency" {
                            value "0";
                        }
                        enum "Alert" {
                            value "1";
                        }
                        enum "Critical" {
                            value "2";
                        }
                        enum "Error" {
                            value "3";
                        }
                        enum "Warning" {
                            value "4";
                        }
                        enum "Notice" {
                            value "5";
                        }
                        enum "Informational" {
                            value "6";
                        }
                        enum "Debug" {
                            value "7";
                        }
                    }
                    must "not ((. = 'Emergency' and (/config_data/auth/CnfAuth/RR_CnfAuthCnfVersion >= 0)) or (. = 'Alert' and (/config_data/auth/CnfAuth/RR_CnfAuthCnfVersion >= 0)) or (. = 'Error' and (/config_data/auth/CnfAuth/RR_CnfAuthCnfVersion >= 0)) or (. = 'Warning' and (/config_data/auth/CnfAuth/RR_CnfAuthCnfVersion >= 0)) or (. = 'Notice' and (/config_data/auth/CnfAuth/RR_CnfAuthCnfVersion >= 0)) or (. = 'Informational' and (/config_data/auth/CnfAuth/RR_CnfAuthCnfVersion >= 0)) or (. = 'Debug' and (/config_data/auth/CnfAuth/RR_CnfAuthCnfVersion >= 0)))";
                }
                leaf "RR_Event_Radio_Blocked_CritTemp_AO" {
                    type "lbox_off_on";
                }
                leaf "RR_Event_Radio_Blocked_CritTemp_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Radio_Blocked_CritTemp_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Radio_Blocked_CritTemp_Snmp" {
                    when "not ((/config_data/main/SNMP/RR_SnmpMode = 'Off') or (/config_data/main/SNMP/RR_SnmpNotification = 'Off'))";
                    type "lbox_off_on";
                }
                leaf "RR_Event_Radio_Blocked_CritTemp_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_Radio_Blocked_CritTemp_HS" {
                    when "not ((/config_data/device/DeviceHw/RR_DynHw_HotStandby != 'On') or (/config_data/main/HotStdby/RR_HotStdby_Enable != 'On'))";
                    type "lbox_off_on";
                }
            }
            container "EventAlarmInput" {
                leaf "RR_Event_Alarm_Input_Sev" {
                    type "lbox_event_severity";
                }
                leaf "RR_Event_Alarm_Input_AO" {
                    type "lbox_off_on";
                }
                leaf "RR_Event_Alarm_Input_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Alarm_Input_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Alarm_Input_Snmp" {
                    when "not ((/config_data/main/SNMP/RR_SnmpNotification = 'Off') or (/config_data/main/SNMP/RR_SnmpMode = 'Off'))";
                    type "lbox_off_on";
                }
                leaf "RR_Event_Alarm_Input_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventDidoInput1" {
                when "not (((/config_data/device/DeviceHw/RR_DynHw_HotStandby = 'On') and (/config_data/main/HotStdby/RR_HotStdby_Enable = 'On')) or (/config_data/device/DeviceHw/RR_DynHw_Port_Dido_Di_Cnt <= 0))";
                leaf "RR_Event_DIDO_Input_1_Sev" {
                    type "lbox_event_severity";
                }
                leaf "RR_Event_DIDO_Input_1_AO" {
                    type "lbox_off_on";
                }
                leaf "RR_Event_DIDO_Input_1_DO1" {
                    when "not (/config_data/device/DeviceHw/RR_DynHw_Port_Dido_Do_Cnt <= 0)";
                    type "lbox_off_on";
                }
                leaf "RR_Event_DIDO_Input_1_DO2" {
                    when "not (/config_data/device/DeviceHw/RR_DynHw_Port_Dido_Do_Cnt <= 1)";
                    type "lbox_off_on";
                }
                leaf "RR_Event_DIDO_Input_1_Snmp" {
                    when "not ((/config_data/main/SNMP/RR_SnmpNotification = 'Off') or (/config_data/main/SNMP/RR_SnmpMode = 'Off'))";
                    type "lbox_off_on";
                }
                leaf "RR_Event_DIDO_Input_1_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventDidoInput2" {
                when "not (((/config_data/device/DeviceHw/RR_DynHw_HotStandby = 'On') and (/config_data/main/HotStdby/RR_HotStdby_Enable = 'On')) or (/config_data/device/DeviceHw/RR_DynHw_Port_Dido_Di_Cnt <= 1))";
                leaf "RR_Event_DIDO_Input_2_Sev" {
                    type "lbox_event_severity";
                }
                leaf "RR_Event_DIDO_Input_2_AO" {
                    type "lbox_off_on";
                }
                leaf "RR_Event_DIDO_Input_2_DO1" {
                    when "not (/config_data/device/DeviceHw/RR_DynHw_Port_Dido_Do_Cnt <= 0)";
                    type "lbox_off_on";
                }
                leaf "RR_Event_DIDO_Input_2_DO2" {
                    when "not (/config_data/device/DeviceHw/RR_DynHw_Port_Dido_Do_Cnt <= 1)";
                    type "lbox_off_on";
                }
                leaf "RR_Event_DIDO_Input_2_Snmp" {
                    when "not ((/config_data/main/SNMP/RR_SnmpNotification = 'Off') or (/config_data/main/SNMP/RR_SnmpMode = 'Off'))";
                    type "lbox_off_on";
                }
                leaf "RR_Event_DIDO_Input_2_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventDidoInput3" {
                when "not (((/config_data/device/DeviceHw/RR_DynHw_HotStandby = 'On') and (/config_data/main/HotStdby/RR_HotStdby_Enable = 'On')) or (/config_data/device/DeviceHw/RR_DynHw_Port_Dido_Di_Cnt <= 2))";
                leaf "RR_Event_DIDO_Input_3_Sev" {
                    type "lbox_event_severity";
                }
                leaf "RR_Event_DIDO_Input_3_AO" {
                    type "lbox_off_on";
                }
                leaf "RR_Event_DIDO_Input_3_DO1" {
                    when "not (/config_data/device/DeviceHw/RR_DynHw_Port_Dido_Do_Cnt <= 0)";
                    type "lbox_off_on";
                }
                leaf "RR_Event_DIDO_Input_3_DO2" {
                    when "not (/config_data/device/DeviceHw/RR_DynHw_Port_Dido_Do_Cnt <= 1)";
                    type "lbox_off_on";
                }
                leaf "RR_Event_DIDO_Input_3_Snmp" {
                    when "not ((/config_data/main/SNMP/RR_SnmpNotification = 'Off') or (/config_data/main/SNMP/RR_SnmpMode = 'Off'))";
                    type "lbox_off_on";
                }
                leaf "RR_Event_DIDO_Input_3_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventTimeSet" {
                leaf "RR_Event_Time_Set_Sev" {
                    type "lbox_event_severity";
                }
                leaf "RR_Event_Time_Set_AO" {
                    type "lbox_off_on";
                }
                leaf "RR_Event_Time_Set_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Time_Set_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Time_Set_Snmp" {
                    when "not ((/config_data/main/SNMP/RR_SnmpNotification = 'Off') or (/config_data/main/SNMP/RR_SnmpMode = 'Off'))";
                    type "lbox_off_on";
                }
                leaf "RR_Event_Time_Set_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventHotStandbyActivate" {
                when "not ((/config_data/device/DeviceHw/RR_DynHw_HotStandby != 'On') or (/config_data/main/HotStdby/RR_HotStdby_Enable != 'On'))";
                leaf "RR_Event_Hot_Standby_Activate_Sev" {
                    type "lbox_event_severity";
                }
                leaf "RR_Event_Hot_Standby_Activate_AO" {
                    type "lbox_off_on";
                }
                leaf "RR_Event_Hot_Standby_Activate_Snmp" {
                    when "not ((/config_data/main/SNMP/RR_SnmpNotification = 'Off') or (/config_data/main/SNMP/RR_SnmpMode = 'Off'))";
                    type "lbox_off_on";
                }
                leaf "RR_Event_Hot_Standby_Activate_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventHotStandbyPassivate" {
                when "not ((/config_data/device/DeviceHw/RR_DynHw_HotStandby != 'On') or (/config_data/main/HotStdby/RR_HotStdby_Enable != 'On'))";
                leaf "RR_Event_Hot_Standby_Passivate_Sev" {
                    type "lbox_event_severity";
                }
                leaf "RR_Event_Hot_Standby_Passivate_AO" {
                    type "lbox_off_on";
                }
                leaf "RR_Event_Hot_Standby_Passivate_Snmp" {
                    when "not ((/config_data/main/SNMP/RR_SnmpNotification = 'Off') or (/config_data/main/SNMP/RR_SnmpMode = 'Off'))";
                    type "lbox_off_on";
                }
                leaf "RR_Event_Hot_Standby_Passivate_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventHotStandbyController" {
                when "not ((/config_data/device/DeviceHw/RR_DynHw_HotStandby != 'On') or (/config_data/main/HotStdby/RR_HotStdby_Enable != 'On'))";
                leaf "RR_Event_Hot_Standby_Controller_Sev" {
                    type "lbox_event_severity";
                }
                leaf "RR_Event_Hot_Standby_Controller_AO" {
                    type "lbox_off_on";
                }
                leaf "RR_Event_Hot_Standby_Controller_Snmp" {
                    when "not ((/config_data/main/SNMP/RR_SnmpNotification = 'Off') or (/config_data/main/SNMP/RR_SnmpMode = 'Off'))";
                    type "lbox_off_on";
                }
                leaf "RR_Event_Hot_Standby_Controller_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventTamperContacts" {
                when "not (/config_data/device/DeviceHw/RR_DynHw_Tamper != 'On')";
                leaf "RR_Event_Tamper_Contacts_Sev" {
                    type "lbox_event_severity";
                }
                leaf "RR_Event_Tamper_Contacts_AO" {
                    type "lbox_off_on";
                }
                leaf "RR_Event_Tamper_Contacts_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Tamper_Contacts_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Tamper_Contacts_Snmp" {
                    when "not ((/config_data/main/SNMP/RR_SnmpNotification = 'Off') or (/config_data/main/SNMP/RR_SnmpMode = 'Off'))";
                    type "lbox_off_on";
                }
                leaf "RR_Event_Tamper_Contacts_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventModemTempLow" {
                leaf "RR_Event_Modem_Temp_Low_Limit" {
                    type "int8" {
                        range "-40..20";
                    }
                }
                leaf "RR_Event_Modem_Temp_Low_Sev" {
                    type "lbox_event_severity";
                }
                leaf "RR_Event_Modem_Temp_Low_AO" {
                    type "lbox_off_on";
                }
                leaf "RR_Event_Modem_Temp_Low_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Modem_Temp_Low_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Modem_Temp_Low_Snmp" {
                    when "not ((/config_data/main/SNMP/RR_SnmpNotification = 'Off') or (/config_data/main/SNMP/RR_SnmpMode = 'Off'))";
                    type "lbox_off_on";
                }
                leaf "RR_Event_Modem_Temp_Low_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_Modem_Temp_Low_HS" {
                    when "not ((/config_data/device/DeviceHw/RR_DynHw_HotStandby != 'On') or (/config_data/main/HotStdby/RR_HotStdby_Enable != 'On'))";
                    type "lbox_off_on";
                }
                leaf "RR_Event_Modem_Temp_Low_Hyst" {
                    type "uint8" {
                        range "1..10";
                    }
                }
            }
            container "EventModemTempHigh" {
                leaf "RR_Event_Modem_Temp_High_Limit" {
                    type "uint8" {
                        range "40..85";
                    }
                }
                leaf "RR_Event_Modem_Temp_High_Sev" {
                    type "lbox_event_severity";
                }
                leaf "RR_Event_Modem_Temp_High_AO" {
                    type "lbox_off_on";
                }
                leaf "RR_Event_Modem_Temp_High_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Modem_Temp_High_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Modem_Temp_High_Snmp" {
                    when "not ((/config_data/main/SNMP/RR_SnmpNotification = 'Off') or (/config_data/main/SNMP/RR_SnmpMode = 'Off'))";
                    type "lbox_off_on";
                }
                leaf "RR_Event_Modem_Temp_High_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_Modem_Temp_High_HS" {
                    when "not ((/config_data/device/DeviceHw/RR_DynHw_HotStandby != 'On') or (/config_data/main/HotStdby/RR_HotStdby_Enable != 'On'))";
                    type "lbox_off_on";
                }
                leaf "RR_Event_Modem_Temp_High_Hyst" {
                    type "uint8" {
                        range "1..10";
                    }
                }
            }
            container "EventCPUTempLow" {
                leaf "RR_Event_CPU_Temp_Low_Limit" {
                    type "int8" {
                        range "-45..20";
                    }
                }
                leaf "RR_Event_CPU_Temp_Low_Sev" {
                    type "lbox_event_severity";
                }
                leaf "RR_Event_CPU_Temp_Low_AO" {
                    type "lbox_off_on";
                }
                leaf "RR_Event_CPU_Temp_Low_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_CPU_Temp_Low_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_CPU_Temp_Low_Snmp" {
                    when "not ((/config_data/main/SNMP/RR_SnmpNotification = 'Off') or (/config_data/main/SNMP/RR_SnmpMode = 'Off'))";
                    type "lbox_off_on";
                }
                leaf "RR_Event_CPU_Temp_Low_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_CPU_Temp_Low_HS" {
                    when "not ((/config_data/device/DeviceHw/RR_DynHw_HotStandby != 'On') or (/config_data/main/HotStdby/RR_HotStdby_Enable != 'On'))";
                    type "lbox_off_on";
                }
                leaf "RR_Event_CPU_Temp_Low_Hyst" {
                    type "uint8" {
                        range "1..10";
                    }
                }
            }
            container "EventCPUTempHigh" {
                leaf "RR_Event_CPU_Temp_High_Limit" {
                    type "uint8" {
                        range "40..115";
                    }
                }
                leaf "RR_Event_CPU_Temp_High_Sev" {
                    type "lbox_event_severity";
                }
                leaf "RR_Event_CPU_Temp_High_AO" {
                    type "lbox_off_on";
                }
                leaf "RR_Event_CPU_Temp_High_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_CPU_Temp_High_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_CPU_Temp_High_Snmp" {
                    when "not ((/config_data/main/SNMP/RR_SnmpNotification = 'Off') or (/config_data/main/SNMP/RR_SnmpMode = 'Off'))";
                    type "lbox_off_on";
                }
                leaf "RR_Event_CPU_Temp_High_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_CPU_Temp_High_HS" {
                    when "not ((/config_data/device/DeviceHw/RR_DynHw_HotStandby != 'On') or (/config_data/main/HotStdby/RR_HotStdby_Enable != 'On'))";
                    type "lbox_off_on";
                }
                leaf "RR_Event_CPU_Temp_High_Hyst" {
                    type "uint8" {
                        range "1..10";
                    }
                }
            }
            container "EventInputVoltageLow" {
                leaf "RR_Event_Input_Voltage_Low_Limit" {
                    type "decimal64" {
                        fraction-digits "1";
                        range "0.0..100.0";
                    }
                    must ". >= /config_data/device/DeviceHw/RR_DynHw_InpVoltage_Min" {
                        error-message "valmsg_it_Event_Input_Voltage_Low_Limit";
                    }
                    must ". <= /config_data/device/DeviceHw/RR_DynHw_InpVoltage_Max" {
                        error-message "valmsg_it_Event_Input_Voltage_Low_Limit";
                    }
                    must ". <= /config_data/main/EventInputVoltageHigh/RR_Event_Input_Voltage_High_Limit" {
                        error-message "valmsg_it_Event_Input_Voltage_Low_Limit";
                    }
                }
                leaf "RR_Event_Input_Voltage_Low_Hyst" {
                    type "decimal64" {
                        fraction-digits "1";
                        range "0.1..2.0";
                    }
                }
                leaf "RR_Event_Input_Voltage_Low_Sev" {
                    type "lbox_event_severity";
                }
                leaf "RR_Event_Input_Voltage_Low_AO" {
                    type "lbox_off_on";
                }
                leaf "RR_Event_Input_Voltage_Low_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Input_Voltage_Low_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Input_Voltage_Low_Snmp" {
                    when "not ((/config_data/main/SNMP/RR_SnmpNotification = 'Off') or (/config_data/main/SNMP/RR_SnmpMode = 'Off'))";
                    type "lbox_off_on";
                }
                leaf "RR_Event_Input_Voltage_Low_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_Input_Voltage_Low_HS" {
                    when "not ((/config_data/device/DeviceHw/RR_DynHw_HotStandby != 'On') or (/config_data/main/HotStdby/RR_HotStdby_Enable != 'On'))";
                    type "lbox_off_on";
                }
            }
            container "EventInputVoltageHigh" {
                leaf "RR_Event_Input_Voltage_High_Limit" {
                    type "decimal64" {
                        fraction-digits "1";
                        range "0.0..100.0";
                    }
                    must ". >= /config_data/device/DeviceHw/RR_DynHw_InpVoltage_Min" {
                        error-message "valmsg_it_Event_Input_Voltage_High_Limit";
                    }
                    must ". <= /config_data/device/DeviceHw/RR_DynHw_InpVoltage_Max" {
                        error-message "valmsg_it_Event_Input_Voltage_High_Limit";
                    }
                    must ". >= /config_data/main/EventInputVoltageLow/RR_Event_Input_Voltage_Low_Limit" {
                        error-message "valmsg_it_Event_Input_Voltage_High_Limit";
                    }
                }
                leaf "RR_Event_Input_Voltage_High_Hyst" {
                    type "decimal64" {
                        fraction-digits "1";
                        range "0.1..2.0";
                    }
                }
                leaf "RR_Event_Input_Voltage_High_Sev" {
                    type "lbox_event_severity";
                }
                leaf "RR_Event_Input_Voltage_High_AO" {
                    type "lbox_off_on";
                }
                leaf "RR_Event_Input_Voltage_High_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Input_Voltage_High_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Input_Voltage_High_Snmp" {
                    when "not ((/config_data/main/SNMP/RR_SnmpNotification = 'Off') or (/config_data/main/SNMP/RR_SnmpMode = 'Off'))";
                    type "lbox_off_on";
                }
                leaf "RR_Event_Input_Voltage_High_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_Input_Voltage_High_HS" {
                    when "not ((/config_data/device/DeviceHw/RR_DynHw_HotStandby != 'On') or (/config_data/main/HotStdby/RR_HotStdby_Enable != 'On'))";
                    type "lbox_off_on";
                }
            }
            container "EventSmsAlarm" {
                when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsCommands != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsCommands != 'On')))";
                leaf "RR_Event_SMS_Alarm_Sev" {
                    type "lbox_event_severity";
                }
                leaf "RR_Event_SMS_Alarm_AO" {
                    type "lbox_off_on";
                }
                leaf "RR_Event_SMS_Alarm_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_SMS_Alarm_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_SMS_Alarm_Snmp" {
                    when "not ((/config_data/main/SNMP/RR_SnmpNotification = 'Off') or (/config_data/main/SNMP/RR_SnmpMode = 'Off'))";
                    type "lbox_off_on";
                }
                leaf "RR_Event_SMS_Alarm_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventSysFwUploaded" {
                leaf "RR_Event_Sys_FW_Uploaded_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_Sys_FW_Uploaded_Snmp" {
                    when "not ((/config_data/main/SNMP/RR_SnmpNotification = 'Off') or (/config_data/main/SNMP/RR_SnmpMode = 'Off'))";
                    type "lbox_off_on";
                }
                leaf "RR_Event_Sys_FW_Uploaded_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventSysFwUploadRej" {
                leaf "RR_Event_Sys_FW_Upload_Rej_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_Sys_FW_Upload_Rej_Snmp" {
                    when "not ((/config_data/main/SNMP/RR_SnmpNotification = 'Off') or (/config_data/main/SNMP/RR_SnmpMode = 'Off'))";
                    type "lbox_off_on";
                }
                leaf "RR_Event_Sys_FW_Upload_Rej_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventSysFwUploadUn" {
                leaf "RR_Event_Sys_FW_Upload_Un_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_Sys_FW_Upload_Un_Snmp" {
                    when "not ((/config_data/main/SNMP/RR_SnmpNotification = 'Off') or (/config_data/main/SNMP/RR_SnmpMode = 'Off'))";
                    type "lbox_off_on";
                }
                leaf "RR_Event_Sys_FW_Upload_Un_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventFDistrSendingStarted" {
                when "not ((/config_data/device/DeviceHw/RR_DynHw_FwDistribution != 'On') or (/config_data/main/FwDistribution/RR_FwDist_SenderEn != 'On'))";
                leaf "RR_Event_FDistr_Sending_Started_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_FDistr_Sending_Started_Snmp" {
                    when "not ((/config_data/main/SNMP/RR_SnmpNotification = 'Off') or (/config_data/main/SNMP/RR_SnmpMode = 'Off'))";
                    type "lbox_off_on";
                }
                leaf "RR_Event_FDistr_Sending_Started_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventFDistrSendingDone" {
                when "not ((/config_data/device/DeviceHw/RR_DynHw_FwDistribution != 'On') or (/config_data/main/FwDistribution/RR_FwDist_SenderEn != 'On'))";
                leaf "RR_Event_FDistr_Sending_Done_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_FDistr_Sending_Done_Snmp" {
                    when "not ((/config_data/main/SNMP/RR_SnmpNotification = 'Off') or (/config_data/main/SNMP/RR_SnmpMode = 'Off'))";
                    type "lbox_off_on";
                }
                leaf "RR_Event_FDistr_Sending_Done_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventFDistrSendingStopped" {
                when "not ((/config_data/device/DeviceHw/RR_DynHw_FwDistribution != 'On') or (/config_data/main/FwDistribution/RR_FwDist_SenderEn != 'On'))";
                leaf "RR_Event_FDistr_Sending_Stopped_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_FDistr_Sending_Stopped_Snmp" {
                    when "not ((/config_data/main/SNMP/RR_SnmpNotification = 'Off') or (/config_data/main/SNMP/RR_SnmpMode = 'Off'))";
                    type "lbox_off_on";
                }
                leaf "RR_Event_FDistr_Sending_Stopped_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventDbContentClearedEvt" {
                leaf "RR_Event_Db_Content_Cleared_Evt_Sev" {
                    type "lbox_event_severity";
                }
            }
            container "EventDbContentClearedStat" {
                leaf "RR_Event_Db_Content_Cleared_Stat_Sev" {
                    type "lbox_event_severity";
                }
            }
            container "EventSysPowerCycle" {
                leaf "RR_Event_Sys_Power_Cycle_Sev" {
                    type "lbox_event_severity";
                }
            }
            container "EventCellMainDown" {
                when "not ((/config_data/device/DeviceHw/RR_DynHw_Primary_Cellular != 'On') or (/config_data/main/Cellular/RR_CellMain_Enable != 'On'))";
                leaf "RR_Event_Cell_Main_Down_Sev" {
                    type "lbox_event_severity";
                }
                leaf "RR_Event_Cell_Main_Down_AO" {
                    type "lbox_off_on";
                }
                leaf "RR_Event_Cell_Main_Down_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Cell_Main_Down_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Cell_Main_Down_Snmp" {
                    when "not ((/config_data/main/SNMP/RR_SnmpNotification = 'Off') or (/config_data/main/SNMP/RR_SnmpMode = 'Off'))";
                    type "lbox_off_on";
                }
                leaf "RR_Event_Cell_Main_Down_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventCellExtDown" {
                when "not ((/config_data/device/DeviceHw/RR_DynHw_Module_Cellular != 'On') or (/config_data/main/Cellular/RR_CellAux_Enable != 'On'))";
                leaf "RR_Event_Cell_Ext_Down_Sev" {
                    type "lbox_event_severity";
                }
                leaf "RR_Event_Cell_Ext_Down_AO" {
                    type "lbox_off_on";
                }
                leaf "RR_Event_Cell_Ext_Down_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Cell_Ext_Down_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Cell_Ext_Down_Snmp" {
                    when "not ((/config_data/main/SNMP/RR_SnmpNotification = 'Off') or (/config_data/main/SNMP/RR_SnmpMode = 'Off'))";
                    type "lbox_off_on";
                }
                leaf "RR_Event_Cell_Ext_Down_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventSleepModeSuspendTime" {
                when "not (/config_data/main/SleepMode/RR_Sleep_Enable != 'On')";
                leaf "RR_Event_Sleep_Susp_Time_Severity" {
                    type "lbox_event_severity";
                }
            }
            container "EventGnssPositionLost" {
                when "not ((/config_data/device/DeviceHw/RR_DynHw_Module_Gps != 'On') or (/config_data/main/Gnss/RR_Gnss_Enable != 'On'))";
                leaf "RR_Event_Gnss_Position_Lost_Sev" {
                    type "lbox_event_severity";
                }
                leaf "RR_Event_Gnss_Position_Lost_AO" {
                    type "lbox_off_on";
                }
                leaf "RR_Event_Gnss_Position_Lost_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Gnss_Position_Lost_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Gnss_Position_Lost_Snmp" {
                    when "not ((/config_data/main/SNMP/RR_SnmpNotification = 'Off') or (/config_data/main/SNMP/RR_SnmpMode = 'Off'))";
                    type "lbox_off_on";
                }
                leaf "RR_Event_Gnss_Position_Lost_Sms" {
                    when "not ((/config_data/device/DeviceHw/RR_DynHw_Primary_Cellular = 'Off') or (/config_data/device/DeviceHw/RR_DynHw_Cell_Main_Sms = 'Off') or (/config_data/main/Cellular/RR_CellMain_Enable = 'Off') or (/config_data/main/CellularMain/RR_CellMain_SmsNotifications = 'Off'))";
                    type "lbox_off_on";
                }
            }
            container "EventGnssPpsSignalLost" {
                when "not ((/config_data/device/DeviceHw/RR_DynHw_Module_Gps != 'On') or (/config_data/main/Gnss/RR_Gnss_Enable != 'On'))";
                leaf "RR_Event_Gnss_Pps_Signal_Lost_Sev" {
                    type "lbox_event_severity";
                }
                leaf "RR_Event_Gnss_Pps_Signal_Lost_AO" {
                    type "lbox_off_on";
                }
                leaf "RR_Event_Gnss_Pps_Signal_Lost_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Gnss_Pps_Signal_Lost_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Gnss_Pps_Signal_Lost_Snmp" {
                    when "not ((/config_data/main/SNMP/RR_SnmpNotification = 'Off') or (/config_data/main/SNMP/RR_SnmpMode = 'Off'))";
                    type "lbox_off_on";
                }
                leaf "RR_Event_Gnss_Pps_Signal_Lost_Sms" {
                    when "not ((/config_data/device/DeviceHw/RR_DynHw_Primary_Cellular = 'Off') or (/config_data/device/DeviceHw/RR_DynHw_Cell_Main_Sms = 'Off') or (/config_data/main/Cellular/RR_CellMain_Enable = 'Off') or (/config_data/main/CellularMain/RR_CellMain_SmsNotifications = 'Off'))";
                    type "lbox_off_on";
                }
            }
            container "EventSleepModeSuspendEvent" {
                when "not (/config_data/main/SleepMode/RR_Sleep_Enable != 'On')";
                leaf "RR_Event_Sleep_Susp_Event_Severity" {
                    type "lbox_event_severity";
                }
            }
            container "EventPpp1LinkDown" {
                when "not ((/config_data/device/DeviceHw/RR_DynHw_Port_Com1 != 'On') or (/config_data/main/ComPort_1/RR_ComPort_1_ENA != 'On') or (/config_data/main/ComPort_1/RR_ComPort_1_Protocol != 'PPP'))";
                leaf "RR_Event_Ppp_1_Link_Down_Sev" {
                    type "lbox_event_severity";
                }
                leaf "RR_Event_Ppp_1_Link_Down_AO" {
                    type "lbox_off_on";
                }
                leaf "RR_Event_Ppp_1_Link_Down_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Ppp_1_Link_Down_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Ppp_1_Link_Down_Snmp" {
                    when "not ((/config_data/main/SNMP/RR_SnmpNotification = 'Off') or (/config_data/main/SNMP/RR_SnmpMode = 'Off'))";
                    type "lbox_off_on";
                }
                leaf "RR_Event_Ppp_1_Link_Down_Sms" {
                    when "not (((/config_data/device/DeviceHw/RR_DynHw_Primary_Cellular = 'Off') or (/config_data/device/DeviceHw/RR_DynHw_Cell_Main_Sms = 'Off') or (/config_data/main/Cellular/RR_CellMain_Enable = 'Off') or (/config_data/main/CellularMain/RR_CellMain_SmsNotifications = 'Off')) and ((/config_data/device/DeviceHw/RR_DynHw_Module_Cellular = 'Off') or (/config_data/device/DeviceHw/RR_DynHw_Cell_Ext_Sms = 'Off') or (/config_data/main/Cellular/RR_CellAux_Enable = 'Off') or (/config_data/main/CellularAux/RR_CellAux_SmsNotifications = 'Off')))";
                    type "lbox_off_on";
                }
            }
            container "EventPpp2LinkDown" {
                when "not ((/config_data/device/DeviceHw/RR_DynHw_Port_Com2 != 'On') or (/config_data/main/ComPort_2/RR_ComPort_2_ENA != 'On') or (/config_data/main/ComPort_2/RR_ComPort_2_Protocol != 'PPP'))";
                leaf "RR_Event_Ppp_2_Link_Down_Sev" {
                    type "lbox_event_severity";
                }
                leaf "RR_Event_Ppp_2_Link_Down_AO" {
                    type "lbox_off_on";
                }
                leaf "RR_Event_Ppp_2_Link_Down_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Ppp_2_Link_Down_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Ppp_2_Link_Down_Snmp" {
                    when "not ((/config_data/main/SNMP/RR_SnmpNotification = 'Off') or (/config_data/main/SNMP/RR_SnmpMode = 'Off'))";
                    type "lbox_off_on";
                }
                leaf "RR_Event_Ppp_2_Link_Down_Sms" {
                    when "not (((/config_data/device/DeviceHw/RR_DynHw_Primary_Cellular = 'Off') or (/config_data/device/DeviceHw/RR_DynHw_Cell_Main_Sms = 'Off') or (/config_data/main/Cellular/RR_CellMain_Enable = 'Off') or (/config_data/main/CellularMain/RR_CellMain_SmsNotifications = 'Off')) and ((/config_data/device/DeviceHw/RR_DynHw_Module_Cellular = 'Off') or (/config_data/device/DeviceHw/RR_DynHw_Cell_Ext_Sms = 'Off') or (/config_data/main/Cellular/RR_CellAux_Enable = 'Off') or (/config_data/main/CellularAux/RR_CellAux_SmsNotifications = 'Off')))";
                    type "lbox_off_on";
                }
            }
            container "EventPpp3LinkDown" {
                when "not ((/config_data/device/DeviceHw/RR_DynHw_Port_Com3 != 'On') or (/config_data/main/ComPort_3/RR_ComPort_3_ENA != 'On') or (/config_data/main/ComPort_3/RR_ComPort_3_Protocol != 'PPP'))";
                leaf "RR_Event_Ppp_3_Link_Down_Sev" {
                    type "lbox_event_severity";
                }
                leaf "RR_Event_Ppp_3_Link_Down_AO" {
                    type "lbox_off_on";
                }
                leaf "RR_Event_Ppp_3_Link_Down_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Ppp_3_Link_Down_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Ppp_3_Link_Down_Snmp" {
                    when "not ((/config_data/main/SNMP/RR_SnmpNotification = 'Off') or (/config_data/main/SNMP/RR_SnmpMode = 'Off'))";
                    type "lbox_off_on";
                }
                leaf "RR_Event_Ppp_3_Link_Down_Sms" {
                    when "not (((/config_data/device/DeviceHw/RR_DynHw_Primary_Cellular = 'Off') or (/config_data/device/DeviceHw/RR_DynHw_Cell_Main_Sms = 'Off') or (/config_data/main/Cellular/RR_CellMain_Enable = 'Off') or (/config_data/main/CellularMain/RR_CellMain_SmsNotifications = 'Off')) and ((/config_data/device/DeviceHw/RR_DynHw_Module_Cellular = 'Off') or (/config_data/device/DeviceHw/RR_DynHw_Cell_Ext_Sms = 'Off') or (/config_data/main/Cellular/RR_CellAux_Enable = 'Off') or (/config_data/main/CellularAux/RR_CellAux_SmsNotifications = 'Off')))";
                    type "lbox_off_on";
                }
            }
            container "EventSysCnfCheckWarning" {
                leaf "RR_Event_Sys_Cnf_Check_Warn_Sev" {
                    type "lbox_event_severity";
                }
                leaf "RR_Event_Sys_Cnf_Check_Warn_Snmp" {
                    when "not ((/config_data/main/SNMP/RR_SnmpNotification = 'Off') or (/config_data/main/SNMP/RR_SnmpMode = 'Off'))";
                    type "lbox_off_on";
                }
                leaf "RR_Event_Sys_Cnf_Check_Warn_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventSysKrngLost" {
                leaf "RR_Event_Sys_Krng_Lost_Sev" {
                    type "lbox_event_severity";
                }
            }
            container "EventSysKrngUpdate" {
                leaf "RR_Event_Sys_Krng_Update_Sev" {
                    type "lbox_event_severity";
                }
                leaf "RR_Event_Sys_Krng_Update_Snmp" {
                    when "not ((/config_data/main/SNMP/RR_SnmpNotification = 'Off') or (/config_data/main/SNMP/RR_SnmpMode = 'Off'))";
                    type "lbox_off_on";
                }
                leaf "RR_Event_Sys_Krng_Update_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventSysKrngDefaultChanged" {
                leaf "RR_Event_Sys_Krng_Def_Changed_Sev" {
                    type "lbox_event_severity";
                }
                leaf "RR_Event_Sys_Krng_Def_Changed_Snmp" {
                    when "not ((/config_data/main/SNMP/RR_SnmpNotification = 'Off') or (/config_data/main/SNMP/RR_SnmpMode = 'Off'))";
                    type "lbox_off_on";
                }
                leaf "RR_Event_Sys_Krng_Def_Changed_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventLinkMngNoLink" {
                when "not (/config_data/main/Networking/RR_LinkManagerEn != 'On')";
                leaf "RR_Event_Link_Mng_No_Link_Sev" {
                    type "lbox_event_severity";
                }
                leaf "RR_Event_Link_Mng_No_Link_AO" {
                    type "lbox_off_on";
                }
                leaf "RR_Event_Link_Mng_No_Link_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Link_Mng_No_Link_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Link_Mng_No_Link_Snmp" {
                    when "not ((/config_data/main/SNMP/RR_SnmpNotification = 'Off') or (/config_data/main/SNMP/RR_SnmpMode = 'Off'))";
                    type "lbox_off_on";
                }
                leaf "RR_Event_Link_Mng_No_Link_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
                leaf "RR_Event_Link_Mng_No_Link_HS" {
                    when "not ((/config_data/device/DeviceHw/RR_DynHw_HotStandby != 'On') or (/config_data/main/HotStdby/RR_HotStdby_Enable != 'On'))";
                    type "lbox_off_on";
                }
            }
            container "EventLinkMngLinkSwitch" {
                when "not (/config_data/main/Networking/RR_LinkManagerEn != 'On')";
                leaf "RR_Event_Link_Mng_Link_Switch_Sev" {
                    type "lbox_event_severity";
                }
                leaf "RR_Event_Link_Mng_Link_Switch_Snmp" {
                    when "not ((/config_data/main/SNMP/RR_SnmpNotification = 'Off') or (/config_data/main/SNMP/RR_SnmpMode = 'Off'))";
                    type "lbox_off_on";
                }
                leaf "RR_Event_Link_Mng_Link_Switch_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventLinkMngPrimaryDown" {
                when "not (/config_data/main/Networking/RR_LinkManagerEn != 'On')";
                leaf "RR_Event_Link_Mng_Primary_Down_Sev" {
                    type "lbox_event_severity";
                }
                leaf "RR_Event_Link_Mng_Primary_Down_AO" {
                    type "lbox_off_on";
                }
                leaf "RR_Event_Link_Mng_Primary_Down_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Link_Mng_Primary_Down_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Link_Mng_Primary_Down_Snmp" {
                    when "not ((/config_data/main/SNMP/RR_SnmpNotification = 'Off') or (/config_data/main/SNMP/RR_SnmpMode = 'Off'))";
                    type "lbox_off_on";
                }
                leaf "RR_Event_Link_Mng_Primary_Down_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventOpenVpnClientConnect" {
                when "not (/config_data/main/VPN/RR_OpenVpnEnable != 'On')";
                leaf "RR_Event_OpenVpn_Client_Connect_Sev" {
                    type "lbox_event_severity";
                }
                leaf "RR_Event_OpenVpn_Client_Connect_Snmp" {
                    when "not ((/config_data/main/SNMP/RR_SnmpNotification = 'Off') or (/config_data/main/SNMP/RR_SnmpMode = 'Off'))";
                    type "lbox_off_on";
                }
                leaf "RR_Event_OpenVpn_Client_Connect_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventOpenVpnClientDisconnect" {
                when "not (/config_data/main/VPN/RR_OpenVpnEnable != 'On')";
                leaf "RR_Event_OpenVpn_Client_Disconnect_Sev" {
                    type "lbox_event_severity";
                }
                leaf "RR_Event_OpenVpn_Client_Disconnect_Snmp" {
                    when "not ((/config_data/main/SNMP/RR_SnmpNotification = 'Off') or (/config_data/main/SNMP/RR_SnmpMode = 'Off'))";
                    type "lbox_off_on";
                }
                leaf "RR_Event_OpenVpn_Client_Disconnect_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventOpenVpnConnectionDown1" {
                when "not (/config_data/main/VPN/RR_OpenVpnEnable != 'On')";
                leaf "RR_Event_OpenVpn_Connection_Down_1_Sev" {
                    type "lbox_event_severity";
                }
                leaf "RR_Event_OpenVpn_Connection_Down_1_AO" {
                    type "lbox_off_on";
                }
                leaf "RR_Event_OpenVpn_Connection_Down_1_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_OpenVpn_Connection_Down_1_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_OpenVpn_Connection_Down_1_Snmp" {
                    when "not ((/config_data/main/SNMP/RR_SnmpNotification = 'Off') or (/config_data/main/SNMP/RR_SnmpMode = 'Off'))";
                    type "lbox_off_on";
                }
                leaf "RR_Event_OpenVpn_Connection_Down_1_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventOpenVpnConnectionDown2" {
                when "not (/config_data/main/VPN/RR_OpenVpnEnable != 'On')";
                leaf "RR_Event_OpenVpn_Connection_Down_2_Sev" {
                    type "lbox_event_severity";
                }
                leaf "RR_Event_OpenVpn_Connection_Down_2_AO" {
                    type "lbox_off_on";
                }
                leaf "RR_Event_OpenVpn_Connection_Down_2_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_OpenVpn_Connection_Down_2_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_OpenVpn_Connection_Down_2_Snmp" {
                    when "not ((/config_data/main/SNMP/RR_SnmpNotification = 'Off') or (/config_data/main/SNMP/RR_SnmpMode = 'Off'))";
                    type "lbox_off_on";
                }
                leaf "RR_Event_OpenVpn_Connection_Down_2_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventOpenVpnConnectionDown3" {
                when "not (/config_data/main/VPN/RR_OpenVpnEnable != 'On')";
                leaf "RR_Event_OpenVpn_Connection_Down_3_Sev" {
                    type "lbox_event_severity";
                }
                leaf "RR_Event_OpenVpn_Connection_Down_3_AO" {
                    type "lbox_off_on";
                }
                leaf "RR_Event_OpenVpn_Connection_Down_3_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_OpenVpn_Connection_Down_3_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_OpenVpn_Connection_Down_3_Snmp" {
                    when "not ((/config_data/main/SNMP/RR_SnmpNotification = 'Off') or (/config_data/main/SNMP/RR_SnmpMode = 'Off'))";
                    type "lbox_off_on";
                }
                leaf "RR_Event_OpenVpn_Connection_Down_3_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventOpenVpnConnectionDown4" {
                when "not (/config_data/main/VPN/RR_OpenVpnEnable != 'On')";
                leaf "RR_Event_OpenVpn_Connection_Down_4_Sev" {
                    type "lbox_event_severity";
                }
                leaf "RR_Event_OpenVpn_Connection_Down_4_AO" {
                    type "lbox_off_on";
                }
                leaf "RR_Event_OpenVpn_Connection_Down_4_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_OpenVpn_Connection_Down_4_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_OpenVpn_Connection_Down_4_Snmp" {
                    when "not ((/config_data/main/SNMP/RR_SnmpNotification = 'Off') or (/config_data/main/SNMP/RR_SnmpMode = 'Off'))";
                    type "lbox_off_on";
                }
                leaf "RR_Event_OpenVpn_Connection_Down_4_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventPppOeLinkDown" {
                when "not (/config_data/main/Networking/RR_PppoeClient_Enable != 'On')";
                leaf "RR_Event_Ppp_Oe_Link_Down_Sev" {
                    type "lbox_event_severity";
                }
                leaf "RR_Event_Ppp_Oe_Link_Down_AO" {
                    type "lbox_off_on";
                }
                leaf "RR_Event_Ppp_Oe_Link_Down_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Ppp_Oe_Link_Down_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Ppp_Oe_Link_Down_Snmp" {
                    when "not ((/config_data/main/SNMP/RR_SnmpNotification = 'Off') or (/config_data/main/SNMP/RR_SnmpMode = 'Off'))";
                    type "lbox_off_on";
                }
                leaf "RR_Event_Ppp_Oe_Link_Down_Sms" {
                    when "not (((/config_data/device/DeviceHw/RR_DynHw_Primary_Cellular = 'Off') or (/config_data/device/DeviceHw/RR_DynHw_Cell_Main_Sms = 'Off') or (/config_data/main/Cellular/RR_CellMain_Enable = 'Off') or (/config_data/main/CellularMain/RR_CellMain_SmsNotifications = 'Off')) and ((/config_data/device/DeviceHw/RR_DynHw_Module_Cellular = 'Off') or (/config_data/device/DeviceHw/RR_DynHw_Cell_Ext_Sms = 'Off') or (/config_data/main/Cellular/RR_CellAux_Enable = 'Off') or (/config_data/main/CellularAux/RR_CellAux_SmsNotifications = 'Off')))";
                    type "lbox_off_on";
                }
            }
            container "EventModemIntFault" {
                leaf "RR_Event_Modem_IntFault_Sev" {
                    type "lbox_event_severity";
                }
                leaf "RR_Event_Modem_IntFault_AO" {
                    type "lbox_off_on";
                }
                leaf "RR_Event_Modem_IntFault_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Modem_IntFault_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Modem_IntFault_Hs" {
                    when "not ((/config_data/device/DeviceHw/RR_DynHw_HotStandby != 'On') or (/config_data/main/HotStdby/RR_HotStdby_Enable != 'On'))";
                    type "lbox_off_on";
                }
            }
            container "EventWifiExtApClientConnect" {
                when "not ((/config_data/main/Wifi/RR_WifiExt_Enable != 'On') or (/config_data/main/WifiExt/RR_WifiExt_OperationType != 'LB_wifi_operation_type_Ap'))";
                leaf "RR_Event_WifiExt_Ap_Client_Connect_Sev" {
                    type "lbox_event_severity";
                }
                leaf "RR_Event_WifiExt_Ap_Client_Connect_Snmp" {
                    when "not ((/config_data/main/SNMP/RR_SnmpNotification = 'Off') or (/config_data/main/SNMP/RR_SnmpMode = 'Off'))";
                    type "lbox_off_on";
                }
                leaf "RR_Event_WifiExt_Ap_Client_Connect_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventWifiExtApClientDisconnect" {
                when "not ((/config_data/main/Wifi/RR_WifiExt_Enable != 'On') or (/config_data/main/WifiExt/RR_WifiExt_OperationType != 'LB_wifi_operation_type_Ap'))";
                leaf "RR_Event_WifiExt_Ap_Client_Disconnect_Sev" {
                    type "lbox_event_severity";
                }
                leaf "RR_Event_WifiExt_Ap_Client_Disconnect_Snmp" {
                    when "not ((/config_data/main/SNMP/RR_SnmpNotification = 'Off') or (/config_data/main/SNMP/RR_SnmpMode = 'Off'))";
                    type "lbox_off_on";
                }
                leaf "RR_Event_WifiExt_Ap_Client_Disconnect_Sms" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsNotifications != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsNotifications != 'On')))";
                    type "lbox_off_on";
                }
            }
            container "EventTest" {
                leaf "RR_Event_Test_Sev" {
                    type "lbox_event_severity";
                }
                leaf "RR_Event_Test_AO" {
                    type "lbox_off_on";
                }
                leaf "RR_Event_Test_DO1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_off_on";
                }
                leaf "RR_Event_Test_DO2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_off_on";
                }
                leaf "RR_Event_Test_Snmp" {
                    when "not ((/config_data/main/SNMP/RR_SnmpNotification = 'Off') or (/config_data/main/SNMP/RR_SnmpMode = 'Off'))";
                    type "lbox_off_on";
                }
                leaf "RR_Event_Test_Sms" {
                    when "not (((/config_data/device/DeviceHw/RR_DynHw_Primary_Cellular = 'Off') or (/config_data/device/DeviceHw/RR_DynHw_Cell_Main_Sms = 'Off') or (/config_data/main/Cellular/RR_CellMain_Enable = 'Off') or (/config_data/main/CellularMain/RR_CellMain_SmsNotifications = 'Off')) and ((/config_data/device/DeviceHw/RR_DynHw_Module_Cellular = 'Off') or (/config_data/device/DeviceHw/RR_DynHw_Cell_Ext_Sms = 'Off') or (/config_data/main/Cellular/RR_CellAux_Enable = 'Off') or (/config_data/main/CellularAux/RR_CellAux_SmsNotifications = 'Off')))";
                    type "lbox_off_on";
                }
                leaf "RR_Event_Test_Hs" {
                    when "not ((/config_data/device/DeviceHw/RR_DynHw_HotStandby != 'On') or (/config_data/main/HotStdby/RR_HotStdby_Enable != 'On'))";
                    type "lbox_off_on";
                }
                leaf "RR_Event_Test_Duration" {
                    type "lim_uint_8_1toFF";
                }
            }
            container "EventSysModuleFwInstalled" {
                when "not ((/config_data/device/DeviceHw/RR_DynHw_Primary_Cellular != 'On') and (/config_data/device/DeviceHw/RR_DynHw_Module_Cellular != 'On'))";
                leaf "RR_Event_Sys_Module_FW_Installed_Sev" {
                    type "lbox_event_severity";
                }
                leaf "RR_Event_Sys_Module_FW_Installed_Snmp" {
                    when "not ((/config_data/main/SNMP/RR_SnmpNotification = 'Off') or (/config_data/main/SNMP/RR_SnmpMode = 'Off'))";
                    type "lbox_off_on";
                }
            }
            container "EventNetconfAccessLogin" {
                leaf "RR_Event_Netconf_Access_Login_Sev" {
                    type "lbox_event_severity_warn_up";
                    must "not ((. = 'Emergency' and (/config_data/auth/CnfAuth/RR_CnfAuthCnfVersion >= 0)) or (. = 'Alert' and (/config_data/auth/CnfAuth/RR_CnfAuthCnfVersion >= 0)) or (. = 'Critical' and (/config_data/auth/CnfAuth/RR_CnfAuthCnfVersion >= 0)) or (. = 'Error' and (/config_data/auth/CnfAuth/RR_CnfAuthCnfVersion >= 0)))";
                }
                leaf "RR_Event_Netconf_Access_Login_Snmp" {
                    when "not ((/config_data/main/SNMP/RR_SnmpNotification = 'Off') or (/config_data/main/SNMP/RR_SnmpMode = 'Off'))";
                    type "lbox_off_on";
                }
            }
            container "RadioInterface" {
                when "not (/config_data/device/DeviceHw/RR_DynHw_Primary_Radio != 'On')";
                leaf "RR_ArpTriesCnt" {
                    type "uint8" {
                        range "0..15";
                    }
                }
                leaf "RR_ArpReachTime" {
                    type "uint16" {
                        range "1..3579";
                    }
                }
                leaf "RR_RadioIpAddr" {
                    when "not (/config_data/main/RadioInterface/RR_RadioIfMode != 'Router')";
                    type "inet:ipv4-address";
                }
                leaf "RR_RadioMngEn" {
                    type "lbox_off_on";
                }
                leaf "RR_RadioBabelFilterEn" {
                    when "not ((/config_data/main/Networking/RR_AdvancedDynRouting != 'On') or (/config_data/main/AdvDynamicRouting/RR_ADR_BabelEn != 'On'))";
                    type "lbox_off_on";
                }
                leaf "RR_RadioIpMask" {
                    when "not (/config_data/main/RadioInterface/RR_RadioIfMode != 'Router')";
                    type "lim_ipv4_mask";
                }
                leaf "RR_RadioIfMode" {
                    type "enumeration" {
                        enum "Bridge" {
                            value "1";
                        }
                        enum "Router" {
                            value "2";
                        }
                    }
                }
                leaf "RR_RadioRmtAccEn" {
                    when "not (/config_data/main/UserAccess/RR_UsAcc_RmtAccess_Enable != 'On')";
                    type "lbox_off_on";
                }
                leaf "RR_RadioIfaceMtu" {
                    type "uint16" {
                        range "70..1500";
                    }
                }
                leaf "RR_RadioGratArpBcastEn" {
                    when "not (/config_data/main/RadioProtocol/RR_RadioAccessProtocol != 'Flexible' and /config_data/main/RadioProtocol/RR_RadioAccessProtocol != 'Base driven')";
                    type "lbox_off_on";
                }
                leaf "RR_RadioGratArpBcastInterval" {
                    when "not ((/config_data/main/RadioProtocol/RR_RadioAccessProtocol != 'Flexible' and /config_data/main/RadioProtocol/RR_RadioAccessProtocol != 'Base driven') or (/config_data/main/RadioInterface/RR_RadioGratArpBcastEn != 'On'))";
                    type "uint8" {
                        range "1..24";
                    }
                }
            }
            container "RadioBabelFilter" {
                when "not ((/config_data/device/DeviceHw/RR_DynHw_Primary_Radio != 'On') or (/config_data/main/Networking/RR_AdvancedDynRouting != 'On') or (/config_data/main/AdvDynamicRouting/RR_ADR_BabelEn != 'On') or (/config_data/main/RadioInterface/RR_RadioBabelFilterEn != 'On'))";
                leaf "RR_RadioBblFlt_RssThr_Soft" {
                    type "lim_babelflt_rss";
                    must ". <= /config_data/main/RadioBabelFilter/RR_RadioBblFlt_RssThr_Hard" {
                        error-message "valmsg_it_RadioBblFlt_RssThr_Soft";
                    }
                }
                leaf "RR_RadioBblFlt_RssThr_Hard" {
                    type "lim_babelflt_rss";
                    must ". >= /config_data/main/RadioBabelFilter/RR_RadioBblFlt_RssThr_Soft" {
                        error-message "valmsg_it_RadioBblFlt_RssThr_Hard";
                    }
                }
                leaf "RR_RadioBblFlt_MseThr_Soft" {
                    type "lim_babelflt_mse";
                    must ". >= /config_data/main/RadioBabelFilter/RR_RadioBblFlt_MseThr_Hard" {
                        error-message "valmsg_it_RadioBblFlt_MseThr_Soft";
                    }
                }
                leaf "RR_RadioBblFlt_MseThr_Hard" {
                    type "lim_babelflt_mse";
                    must ". <= /config_data/main/RadioBabelFilter/RR_RadioBblFlt_MseThr_Soft" {
                        error-message "valmsg_it_RadioBblFlt_MseThr_Hard";
                    }
                }
            }
            container "RadioChannel" {
                when "not (/config_data/device/DeviceHw/RR_DynHw_Primary_Radio != 'On')";
                leaf "RR_RadioMaxDistance" {
                    type "uint8" {
                        range "0..200";
                    }
                }
                leaf "RR_RadioFreqTx" {
                    type "uint32" {
                        range "100000000..999999999";
                    }
                    must ". >= /config_data/device/DeviceHw/RR_DynHw_FreqTx_Min" {
                        error-message "valmsg_it_RadioFreqTx";
                    }
                    must ". <= /config_data/device/DeviceHw/RR_DynHw_FreqTx_Max" {
                        error-message "valmsg_it_RadioFreqTx";
                    }
                    must "(. >= /config_data/device/DeviceHw/RR_DynHw_Radio_Freq_ChanL_Min and . <= /config_data/device/DeviceHw/RR_DynHw_Radio_Freq_ChanL_Max) or (. >= /config_data/device/DeviceHw/RR_DynHw_Radio_Freq_ChanH_Min and . <= /config_data/device/DeviceHw/RR_DynHw_Radio_Freq_ChanH_Max)" {
                        error-message "valmsg_it_RadioFreqTx";
                    }
                    must "(. >= /config_data/region/Region/RR_DynReg_FreqInterval_0_Min and . <= /config_data/region/Region/RR_DynReg_FreqInterval_0_Max) or (. >= /config_data/region/Region/RR_DynReg_FreqInterval_1_Min and . <= /config_data/region/Region/RR_DynReg_FreqInterval_1_Max) or (. >= /config_data/region/Region/RR_DynReg_FreqInterval_2_Min and . <= /config_data/region/Region/RR_DynReg_FreqInterval_2_Max) or (. >= /config_data/region/Region/RR_DynReg_FreqInterval_3_Min and . <= /config_data/region/Region/RR_DynReg_FreqInterval_3_Max) or (. >= /config_data/region/Region/RR_DynReg_FreqInterval_4_Min and . <= /config_data/region/Region/RR_DynReg_FreqInterval_4_Max) or (. >= /config_data/region/Region/RR_DynReg_FreqInterval_5_Min and . <= /config_data/region/Region/RR_DynReg_FreqInterval_5_Max) or (. >= /config_data/region/Region/RR_DynReg_FreqInterval_6_Min and . <= /config_data/region/Region/RR_DynReg_FreqInterval_6_Max) or (. >= /config_data/region/Region/RR_DynReg_FreqInterval_7_Min and . <= /config_data/region/Region/RR_DynReg_FreqInterval_7_Max)" {
                        error-message "valmsg_it_RadioFreqTx";
                    }
                }
                leaf "RR_RadioFreqRx" {
                    type "lim_RadioFreqTx_M3";
                    must ". >= /config_data/device/DeviceHw/RR_DynHw_FreqRx_Min" {
                        error-message "valmsg_it_RadioFreqRx";
                    }
                    must ". <= /config_data/device/DeviceHw/RR_DynHw_FreqRx_Max" {
                        error-message "valmsg_it_RadioFreqRx";
                    }
                    must "(. >= /config_data/device/DeviceHw/RR_DynHw_Radio_Freq_ChanL_Min and . <= /config_data/device/DeviceHw/RR_DynHw_Radio_Freq_ChanL_Max) or (. >= /config_data/device/DeviceHw/RR_DynHw_Radio_Freq_ChanH_Min and . <= /config_data/device/DeviceHw/RR_DynHw_Radio_Freq_ChanH_Max)" {
                        error-message "valmsg_it_RadioFreqRx";
                    }
                    must "(. >= /config_data/region/Region/RR_DynReg_FreqInterval_0_Min and . <= /config_data/region/Region/RR_DynReg_FreqInterval_0_Max) or (. >= /config_data/region/Region/RR_DynReg_FreqInterval_1_Min and . <= /config_data/region/Region/RR_DynReg_FreqInterval_1_Max) or (. >= /config_data/region/Region/RR_DynReg_FreqInterval_2_Min and . <= /config_data/region/Region/RR_DynReg_FreqInterval_2_Max) or (. >= /config_data/region/Region/RR_DynReg_FreqInterval_3_Min and . <= /config_data/region/Region/RR_DynReg_FreqInterval_3_Max) or (. >= /config_data/region/Region/RR_DynReg_FreqInterval_4_Min and . <= /config_data/region/Region/RR_DynReg_FreqInterval_4_Max) or (. >= /config_data/region/Region/RR_DynReg_FreqInterval_5_Min and . <= /config_data/region/Region/RR_DynReg_FreqInterval_5_Max) or (. >= /config_data/region/Region/RR_DynReg_FreqInterval_6_Min and . <= /config_data/region/Region/RR_DynReg_FreqInterval_6_Max) or (. >= /config_data/region/Region/RR_DynReg_FreqInterval_7_Min and . <= /config_data/region/Region/RR_DynReg_FreqInterval_7_Max)" {
                        error-message "valmsg_it_RadioFreqRx";
                    }
                }
                leaf "RR_RadioAntennaDetEn" {
                    when "not (/config_data/device/DeviceHw/RR_DynHw_Radio_AntennaDet != 'On')";
                    type "lbox_off_on";
                }
                leaf "RR_RadioAntennaConns" {
                    when "not (/config_data/device/DeviceHw/RR_DynHw_Radio_Duplex_Separate_Channels = 'On')";
                    type "enumeration" {
                        enum "Single (Tx/Rx)" {
                            value "0";
                        }
                        enum "Dual (Rx, Tx/Rx)" {
                            value "1";
                        }
                    }
                    must "not ((. = 'Single (Tx/Rx)' and ((/config_data/device/DeviceHw/RR_DynHw_Radio_Duplex_Separate_Channels != 'On') and (/config_data/main/RadioProtocol/RR_RadioAccessProtocol = 'Transparent') and (/config_data/main/RadioProtocolTrans/RR_RadioTrans_CommMode = 'Full Duplex'))) or (. = 'Dual (Rx, Tx/Rx)' and (/config_data/device/DeviceHw/RR_DynHw_Radio_Antenna_Dual != 'On')))";
                }
                leaf "RR_RadioRfPower" {
                    type "enumeration" {
                        enum "20" {
                            value "20";
                        }
                        enum "21" {
                            value "21";
                        }
                        enum "22" {
                            value "22";
                        }
                        enum "23" {
                            value "23";
                        }
                        enum "24" {
                            value "24";
                        }
                        enum "25" {
                            value "25";
                        }
                        enum "26" {
                            value "26";
                        }
                        enum "27" {
                            value "27";
                        }
                        enum "28" {
                            value "28";
                        }
                        enum "29" {
                            value "29";
                        }
                        enum "30" {
                            value "30";
                        }
                        enum "31" {
                            value "31";
                        }
                        enum "32" {
                            value "32";
                        }
                        enum "33" {
                            value "33";
                        }
                        enum "34" {
                            value "34";
                        }
                        enum "35" {
                            value "35";
                        }
                        enum "36" {
                            value "36";
                        }
                        enum "37" {
                            value "37";
                        }
                        enum "38" {
                            value "38";
                        }
                        enum "39" {
                            value "39";
                        }
                        enum "40" {
                            value "40";
                        }
                    }
                    must "not ((. = '20' and (((/config_data/device/DeviceHw/RR_DynHw_Radio_RfPower_Min != '20') and (/config_data/device/DeviceHw/RR_DynHw_Radio_RfPower_Min >= 20)) or ((/config_data/device/DeviceHw/RR_DynHw_Radio_RfPower_Max != '20') and (/config_data/device/DeviceHw/RR_DynHw_Radio_RfPower_Max <= 20)) or (/config_data/region/Region/RR_DynReg_RfPower_Val_20_En != 'On'))) or (. = '21' and (((/config_data/device/DeviceHw/RR_DynHw_Radio_RfPower_Min != '21') and (/config_data/device/DeviceHw/RR_DynHw_Radio_RfPower_Min >= 21)) or ((/config_data/device/DeviceHw/RR_DynHw_Radio_RfPower_Max != '21') and (/config_data/device/DeviceHw/RR_DynHw_Radio_RfPower_Max <= 21)) or (/config_data/region/Region/RR_DynReg_RfPower_Val_21_En != 'On'))) or (. = '22' and (((/config_data/device/DeviceHw/RR_DynHw_Radio_RfPower_Min != '22') and (/config_data/device/DeviceHw/RR_DynHw_Radio_RfPower_Min >= 22)) or ((/config_data/device/DeviceHw/RR_DynHw_Radio_RfPower_Max != '22') and (/config_data/device/DeviceHw/RR_DynHw_Radio_RfPower_Max <= 22)) or (/config_data/region/Region/RR_DynReg_RfPower_Val_22_En != 'On'))) or (. = '23' and (((/config_data/device/DeviceHw/RR_DynHw_Radio_RfPower_Min != '23') and (/config_data/device/DeviceHw/RR_DynHw_Radio_RfPower_Min >= 23)) or ((/config_data/device/DeviceHw/RR_DynHw_Radio_RfPower_Max != '23') and (/config_data/device/DeviceHw/RR_DynHw_Radio_RfPower_Max <= 23)) or (/config_data/region/Region/RR_DynReg_RfPower_Val_23_En != 'On'))) or (. = '24' and (((/config_data/device/DeviceHw/RR_DynHw_Radio_RfPower_Min != '24') and (/config_data/device/DeviceHw/RR_DynHw_Radio_RfPower_Min >= 24)) or ((/config_data/device/DeviceHw/RR_DynHw_Radio_RfPower_Max != '24') and (/config_data/device/DeviceHw/RR_DynHw_Radio_RfPower_Max <= 24)) or (/config_data/region/Region/RR_DynReg_RfPower_Val_24_En != 'On'))) or (. = '25' and (((/config_data/device/DeviceHw/RR_DynHw_Radio_RfPower_Min != '25') and (/config_data/device/DeviceHw/RR_DynHw_Radio_RfPower_Min >= 25)) or ((/config_data/device/DeviceHw/RR_DynHw_Radio_RfPower_Max != '25') and (/config_data/device/DeviceHw/RR_DynHw_Radio_RfPower_Max <= 25)) or (/config_data/region/Region/RR_DynReg_RfPower_Val_25_En != 'On'))) or (. = '26' and (((/config_data/device/DeviceHw/RR_DynHw_Radio_RfPower_Min != '26') and (/config_data/device/DeviceHw/RR_DynHw_Radio_RfPower_Min >= 26)) or ((/config_data/device/DeviceHw/RR_DynHw_Radio_RfPower_Max != '26') and (/config_data/device/DeviceHw/RR_DynHw_Radio_RfPower_Max <= 26)) or (/config_data/region/Region/RR_DynReg_RfPower_Val_26_En != 'On'))) or (. = '27' and (((/config_data/device/DeviceHw/RR_DynHw_Radio_RfPower_Min != '27') and (/config_data/device/DeviceHw/RR_DynHw_Radio_RfPower_Min >= 27)) or ((/config_data/device/DeviceHw/RR_DynHw_Radio_RfPower_Max != '27') and (/config_data/device/DeviceHw/RR_DynHw_Radio_RfPower_Max <= 27)) or (/config_data/region/Region/RR_DynReg_RfPower_Val_27_En != 'On'))) or (. = '28' and (((/config_data/device/DeviceHw/RR_DynHw_Radio_RfPower_Min != '28') and (/config_data/device/DeviceHw/RR_DynHw_Radio_RfPower_Min >= 28)) or ((/config_data/device/DeviceHw/RR_DynHw_Radio_RfPower_Max != '28') and (/config_data/device/DeviceHw/RR_DynHw_Radio_RfPower_Max <= 28)) or (/config_data/region/Region/RR_DynReg_RfPower_Val_28_En != 'On'))) or (. = '29' and (((/config_data/device/DeviceHw/RR_DynHw_Radio_RfPower_Min != '29') and (/config_data/device/DeviceHw/RR_DynHw_Radio_RfPower_Min >= 29)) or ((/config_data/device/DeviceHw/RR_DynHw_Radio_RfPower_Max != '29') and (/config_data/device/DeviceHw/RR_DynHw_Radio_RfPower_Max <= 29)) or (/config_data/region/Region/RR_DynReg_RfPower_Val_29_En != 'On'))) or (. = '30' and (((/config_data/device/DeviceHw/RR_DynHw_Radio_RfPower_Min != '30') and (/config_data/device/DeviceHw/RR_DynHw_Radio_RfPower_Min >= 30)) or ((/config_data/device/DeviceHw/RR_DynHw_Radio_RfPower_Max != '30') and (/config_data/device/DeviceHw/RR_DynHw_Radio_RfPower_Max <= 30)) or (/config_data/region/Region/RR_DynReg_RfPower_Val_30_En != 'On'))) or (. = '31' and (((/config_data/device/DeviceHw/RR_DynHw_Radio_RfPower_Min != '31') and (/config_data/device/DeviceHw/RR_DynHw_Radio_RfPower_Min >= 31)) or ((/config_data/device/DeviceHw/RR_DynHw_Radio_RfPower_Max != '31') and (/config_data/device/DeviceHw/RR_DynHw_Radio_RfPower_Max <= 31)) or (/config_data/region/Region/RR_DynReg_RfPower_Val_31_En != 'On'))) or (. = '32' and (((/config_data/device/DeviceHw/RR_DynHw_Radio_RfPower_Min != '32') and (/config_data/device/DeviceHw/RR_DynHw_Radio_RfPower_Min >= 32)) or ((/config_data/device/DeviceHw/RR_DynHw_Radio_RfPower_Max != '32') and (/config_data/device/DeviceHw/RR_DynHw_Radio_RfPower_Max <= 32)) or (/config_data/region/Region/RR_DynReg_RfPower_Val_32_En != 'On'))) or (. = '33' and (((/config_data/device/DeviceHw/RR_DynHw_Radio_RfPower_Min != '33') and (/config_data/device/DeviceHw/RR_DynHw_Radio_RfPower_Min >= 33)) or ((/config_data/device/DeviceHw/RR_DynHw_Radio_RfPower_Max != '33') and (/config_data/device/DeviceHw/RR_DynHw_Radio_RfPower_Max <= 33)) or (/config_data/region/Region/RR_DynReg_RfPower_Val_33_En != 'On'))) or (. = '34' and (((/config_data/device/DeviceHw/RR_DynHw_Radio_RfPower_Min != '34') and (/config_data/device/DeviceHw/RR_DynHw_Radio_RfPower_Min >= 34)) or ((/config_data/device/DeviceHw/RR_DynHw_Radio_RfPower_Max != '34') and (/config_data/device/DeviceHw/RR_DynHw_Radio_RfPower_Max <= 34)) or (/config_data/region/Region/RR_DynReg_RfPower_Val_34_En != 'On'))) or (. = '35' and (((/config_data/device/DeviceHw/RR_DynHw_Radio_RfPower_Min != '35') and (/config_data/device/DeviceHw/RR_DynHw_Radio_RfPower_Min >= 35)) or ((/config_data/device/DeviceHw/RR_DynHw_Radio_RfPower_Max != '35') and (/config_data/device/DeviceHw/RR_DynHw_Radio_RfPower_Max <= 35)) or (/config_data/region/Region/RR_DynReg_RfPower_Val_35_En != 'On'))) or (. = '36' and (((/config_data/device/DeviceHw/RR_DynHw_Radio_RfPower_Min != '36') and (/config_data/device/DeviceHw/RR_DynHw_Radio_RfPower_Min >= 36)) or ((/config_data/device/DeviceHw/RR_DynHw_Radio_RfPower_Max != '36') and (/config_data/device/DeviceHw/RR_DynHw_Radio_RfPower_Max <= 36)) or (/config_data/region/Region/RR_DynReg_RfPower_Val_36_En != 'On'))) or (. = '37' and (((/config_data/device/DeviceHw/RR_DynHw_Radio_RfPower_Min != '37') and (/config_data/device/DeviceHw/RR_DynHw_Radio_RfPower_Min >= 37)) or ((/config_data/device/DeviceHw/RR_DynHw_Radio_RfPower_Max != '37') and (/config_data/device/DeviceHw/RR_DynHw_Radio_RfPower_Max <= 37)) or (/config_data/region/Region/RR_DynReg_RfPower_Val_37_En != 'On'))) or (. = '38' and ((/config_data/device/DeviceSwKey/RR_SwKey_Flag_radio_rfpower_over_37dBm != 'On') or ((/config_data/device/DeviceHw/RR_DynHw_Radio_RfPower_Min != '38') and (/config_data/device/DeviceHw/RR_DynHw_Radio_RfPower_Min >= 38)) or ((/config_data/device/DeviceHw/RR_DynHw_Radio_RfPower_Max != '38') and (/config_data/device/DeviceHw/RR_DynHw_Radio_RfPower_Max <= 38)) or (/config_data/region/Region/RR_DynReg_RfPower_Val_38_En != 'On'))) or (. = '39' and ((/config_data/device/DeviceSwKey/RR_SwKey_Flag_radio_rfpower_over_37dBm != 'On') or ((/config_data/device/DeviceHw/RR_DynHw_Radio_RfPower_Min != '39') and (/config_data/device/DeviceHw/RR_DynHw_Radio_RfPower_Min >= 39)) or ((/config_data/device/DeviceHw/RR_DynHw_Radio_RfPower_Max != '39') and (/config_data/device/DeviceHw/RR_DynHw_Radio_RfPower_Max <= 39)) or (/config_data/region/Region/RR_DynReg_RfPower_Val_39_En != 'On'))) or (. = '40' and ((/config_data/device/DeviceSwKey/RR_SwKey_Flag_radio_rfpower_over_37dBm != 'On') or ((/config_data/device/DeviceHw/RR_DynHw_Radio_RfPower_Min != '40') and (/config_data/device/DeviceHw/RR_DynHw_Radio_RfPower_Min >= 40)) or ((/config_data/device/DeviceHw/RR_DynHw_Radio_RfPower_Max != '40') and (/config_data/device/DeviceHw/RR_DynHw_Radio_RfPower_Max <= 40)) or (/config_data/region/Region/RR_DynReg_RfPower_Val_40_En != 'On'))))";
                }
                leaf "RR_RadioRxResilience" {
                    type "enumeration" {
                        enum "High sensitivity" {
                            value "2";
                        }
                        enum "Auto" {
                            value "0";
                        }
                        enum "High resilience" {
                            value "1";
                        }
                        enum "User" {
                            value "3";
                        }
                    }
                    must "not ((. = 'Auto' and (/config_data/device/DeviceHw/RR_DynHw_Radio_Resilience_Auto != 'On')))";
                }
                leaf "RR_RadioRxResilienceLevel" {
                    when "not (/config_data/main/RadioChannel/RR_RadioRxResilience != 'User')";
                    type "uint8" {
                        range "0..31";
                    }
                }
                leaf "RR_RadioACMEn" {
                    when "not ((/config_data/main/RadioProtocol/RR_RadioAccessProtocol = 'None') or (/config_data/device/DeviceHw/RR_DynHw_Radio_Acm != 'On'))";
                    type "enumeration" {
                        enum "Off" {
                            value "0";
                        }
                        enum "On" {
                            value "1";
                        }
                    }
                    must "not ((. = 'On' and (/config_data/device/DeviceSwKey/RR_SwKey_Flag_radio_acm != 'On')))";
                }
                leaf "RR_RadioTempTxBreaker" {
                    type "lbox_off_on";
                }
                leaf "RR_RadioRxModeLed" {
                    when "not (/config_data/device/DeviceHw/RR_DynHw_Radio_RxMode_Led != 'On')";
                    type "lbox_off_on";
                }
                leaf "RR_RadioChSpacing" {
                    type "enumeration" {
                        enum "5" {
                            value "9";
                        }
                        enum "6_25" {
                            value "0";
                        }
                        enum "12_5" {
                            value "1";
                        }
                        enum "25" {
                            value "2";
                        }
                        enum "50" {
                            value "3";
                        }
                        enum "100" {
                            value "4";
                        }
                        enum "150" {
                            value "5";
                        }
                        enum "200" {
                            value "6";
                        }
                        enum "250" {
                            value "7";
                        }
                        enum "300" {
                            value "8";
                        }
                        enum "400" {
                            value "10";
                        }
                        enum "625" {
                            value "11";
                        }
                        enum "1250" {
                            value "12";
                        }
                        enum "2500" {
                            value "13";
                        }
                        enum "5000" {
                            value "14";
                        }
                        enum "10000" {
                            value "15";
                        }
                    }
                    must "not ((. = '5' and (/config_data/region/Region/RR_DynReg_ChSpacing_Val_9_En != 'On')) or (. = '6_25' and (/config_data/region/Region/RR_DynReg_ChSpacing_Val_0_En != 'On')) or (. = '12_5' and (/config_data/region/Region/RR_DynReg_ChSpacing_Val_1_En != 'On')) or (. = '25' and (/config_data/region/Region/RR_DynReg_ChSpacing_Val_2_En != 'On')) or (. = '50' and (/config_data/region/Region/RR_DynReg_ChSpacing_Val_3_En != 'On')) or (. = '100' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_4_En != 'On'))) or (. = '150' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_5_En != 'On'))) or (. = '200' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_6_En != 'On'))) or (. = '250' and ((/config_data/main/RadioProtocol/RR_RadioAccessProtocol != 'Transparent' and /config_data/main/RadioProtocol/RR_RadioAccessProtocol != 'None') or (/config_data/device/DeviceHw/RR_DynHw_Radio_ChSpacing_Over_50kHz != 'On') or (/config_data/device/DeviceSwKey/RR_SwKey_Flag_radio_chspacing_over_50kHz != 'On') or (/config_data/region/Region/RR_DynReg_ChSpacing_Val_7_En != 'On'))) or (. = '300' and ((/config_data/main/RadioProtocol/RR_RadioAccessProtocol != 'Transparent' and /config_data/main/RadioProtocol/RR_RadioAccessProtocol != 'None') or (/config_data/device/DeviceHw/RR_DynHw_Radio_ChSpacing_Over_50kHz != 'On') or (/config_data/device/DeviceSwKey/RR_SwKey_Flag_radio_chspacing_over_50kHz != 'On') or (/config_data/region/Region/RR_DynReg_ChSpacing_Val_8_En != 'On'))) or (. = '400' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_10_En != 'On'))) or (. = '625' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_11_En != 'On'))) or (. = '1250' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_12_En != 'On'))) or (. = '2500' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_13_En != 'On'))) or (. = '5000' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_14_En != 'On'))) or (. = '10000' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_15_En != 'On'))))";
                }
                leaf "RR_RadioChOccupied" {
                    type "enumeration" {
                        enum "5" {
                            value "0";
                        }
                        enum "6_25" {
                            value "1";
                        }
                        enum "11" {
                            value "2";
                        }
                        enum "12_5" {
                            value "3";
                        }
                        enum "14" {
                            value "18";
                        }
                        enum "16" {
                            value "4";
                        }
                        enum "20" {
                            value "5";
                        }
                        enum "25" {
                            value "6";
                        }
                        enum "40" {
                            value "7";
                        }
                        enum "50" {
                            value "8";
                        }
                        enum "80" {
                            value "9";
                        }
                        enum "100" {
                            value "16";
                        }
                        enum "125" {
                            value "10";
                        }
                        enum "150" {
                            value "17";
                        }
                        enum "175" {
                            value "11";
                        }
                        enum "200" {
                            value "12";
                        }
                        enum "225" {
                            value "13";
                        }
                        enum "250" {
                            value "14";
                        }
                        enum "300" {
                            value "15";
                        }
                        enum "400" {
                            value "19";
                        }
                        enum "625" {
                            value "20";
                        }
                        enum "1250" {
                            value "21";
                        }
                        enum "2500" {
                            value "22";
                        }
                        enum "5000" {
                            value "23";
                        }
                        enum "10000" {
                            value "24";
                        }
                    }
                    must "not ((. = '5' and ((/config_data/main/RadioChannel/RR_RadioChSpacing != '5' and /config_data/main/RadioChannel/RR_RadioChSpacing != '6_25') or (/config_data/region/Region/RR_DynReg_ChOccupied_Val_0_En != 'On'))) or (. = '6_25' and (/config_data/auth/CnfAuth/RR_CnfAuthCnfVersion >= 0)) or (. = '11' and ((/config_data/main/RadioChannel/RR_RadioChSpacing != '12_5') or (/config_data/region/Region/RR_DynReg_ChOccupied_Val_2_En != 'On'))) or (. = '12_5' and ((/config_data/main/RadioChannel/RR_RadioChSpacing != '12_5') or (/config_data/main/RadioChannel/RR_RadioModType != 'QAM') or (/config_data/region/Region/RR_DynReg_ChOccupied_Val_3_En != 'On'))) or (. = '14' and ((/config_data/main/RadioChannel/RR_RadioChSpacing != '25') or (/config_data/main/RadioChannel/RR_RadioModType != 'FSK') or (/config_data/region/Region/RR_DynReg_ChOccupied_Val_18_En != 'On'))) or (. = '16' and ((/config_data/main/RadioChannel/RR_RadioChSpacing != '25') or (/config_data/region/Region/RR_DynReg_ChOccupied_Val_4_En != 'On'))) or (. = '20' and ((/config_data/main/RadioChannel/RR_RadioChSpacing != '25') or ((/config_data/device/DeviceHw/RR_DynHw_Radio_Channel_Modulation_Constraint = 'RipEX2') and (/config_data/main/RadioChannel/RR_RadioModType != 'QAM')) or (/config_data/region/Region/RR_DynReg_ChOccupied_Val_5_En != 'On'))) or (. = '25' and ((/config_data/main/RadioChannel/RR_RadioChSpacing != '25') or ((/config_data/device/DeviceHw/RR_DynHw_Radio_Channel_Modulation_Constraint = 'RipEX2') and (/config_data/main/RadioChannel/RR_RadioModType != 'QAM')) or (/config_data/region/Region/RR_DynReg_ChOccupied_Val_6_En != 'On'))) or (. = '40' and ((/config_data/main/RadioChannel/RR_RadioChSpacing != '50') or (/config_data/region/Region/RR_DynReg_ChOccupied_Val_7_En != 'On'))) or (. = '50' and ((/config_data/main/RadioChannel/RR_RadioChSpacing != '50') or (/config_data/region/Region/RR_DynReg_ChOccupied_Val_8_En != 'On'))) or (. = '80' and ((/config_data/main/RadioChannel/RR_RadioChSpacing != '100') or (/config_data/region/Region/RR_DynReg_ChOccupied_Val_9_En != 'On'))) or (. = '100' and ((/config_data/main/RadioChannel/RR_RadioChSpacing != '100') or (/config_data/region/Region/RR_DynReg_ChOccupied_Val_16_En != 'On'))) or (. = '125' and ((/config_data/main/RadioChannel/RR_RadioChSpacing != '150') or (/config_data/region/Region/RR_DynReg_ChOccupied_Val_10_En != 'On'))) or (. = '150' and ((/config_data/main/RadioChannel/RR_RadioChSpacing != '150') or (/config_data/region/Region/RR_DynReg_ChOccupied_Val_17_En != 'On'))) or (. = '175' and ((/config_data/main/RadioChannel/RR_RadioChSpacing != '200') or (/config_data/region/Region/RR_DynReg_ChOccupied_Val_11_En != 'On'))) or (. = '200' and ((/config_data/main/RadioChannel/RR_RadioChSpacing != '200') or ((/config_data/device/DeviceHw/RR_DynHw_Radio_Channel_Modulation_Constraint = 'RipEX2') and (/config_data/main/RadioProtocol/RR_RadioAccessProtocol != 'Transparent' and /config_data/main/RadioProtocol/RR_RadioAccessProtocol != 'None')) or (/config_data/region/Region/RR_DynReg_ChOccupied_Val_12_En != 'On'))) or (. = '225' and ((/config_data/main/RadioChannel/RR_RadioChSpacing != '250') or (/config_data/region/Region/RR_DynReg_ChOccupied_Val_13_En != 'On'))) or (. = '250' and ((/config_data/main/RadioChannel/RR_RadioChSpacing != '250') or (/config_data/region/Region/RR_DynReg_ChOccupied_Val_14_En != 'On'))) or (. = '300' and ((/config_data/main/RadioChannel/RR_RadioChSpacing != '300') or (/config_data/region/Region/RR_DynReg_ChOccupied_Val_15_En != 'On'))) or (. = '400' and ((/config_data/main/RadioChannel/RR_RadioChSpacing != '400') or (/config_data/region/Region/RR_DynReg_ChOccupied_Val_19_En != 'On'))) or (. = '625' and ((/config_data/main/RadioChannel/RR_RadioChSpacing != '625') or (/config_data/region/Region/RR_DynReg_ChOccupied_Val_20_En != 'On'))) or (. = '1250' and ((/config_data/main/RadioChannel/RR_RadioChSpacing != '1250') or (/config_data/region/Region/RR_DynReg_ChOccupied_Val_21_En != 'On'))) or (. = '2500' and ((/config_data/main/RadioChannel/RR_RadioChSpacing != '2500') or (/config_data/region/Region/RR_DynReg_ChOccupied_Val_22_En != 'On'))) or (. = '5000' and ((/config_data/main/RadioChannel/RR_RadioChSpacing != '5000') or (/config_data/region/Region/RR_DynReg_ChOccupied_Val_23_En != 'On'))) or (. = '10000' and ((/config_data/main/RadioChannel/RR_RadioChSpacing != '10000') or (/config_data/region/Region/RR_DynReg_ChOccupied_Val_24_En != 'On'))))";
                }
                leaf "RR_RadioModType" {
                    type "enumeration" {
                        enum "FSK" {
                            value "0";
                        }
                        enum "QAM" {
                            value "1";
                        }
                    }
                    must "not ((. = 'FSK' and ((/config_data/device/DeviceHw/RR_DynHw_Radio_ModType_FSK != 'On') or ((/config_data/device/DeviceHw/RR_DynHw_Radio_Channel_Modulation_Constraint = 'RipEX2') and (/config_data/main/RadioChannel/RR_RadioChSpacing != '5' and /config_data/main/RadioChannel/RR_RadioChSpacing != '6_25' and /config_data/main/RadioChannel/RR_RadioChSpacing != '12_5' and /config_data/main/RadioChannel/RR_RadioChSpacing != '25')))) or (. = 'QAM' and (/config_data/device/DeviceHw/RR_DynHw_Radio_ModType_QAM != 'On')))";
                }
                leaf "RR_RadioModulation" {
                    when "not (((/config_data/main/RadioProtocol/RR_RadioAccessProtocol = 'Base driven') and (/config_data/main/RadioProtocolBaseDr/RR_RadioBDP_StationType = 'Remote')) or ((/config_data/main/RadioChannel/RR_RadioACMEn = 'On') and (/config_data/device/DeviceHw/RR_DynHw_Radio_Acm = 'On')))";
                    type "lbox_radio_modulation_M7";
                    must "not ((. = '2CPFSK' and (/config_data/main/RadioChannel/RR_RadioModType != 'FSK')) or (. = '4CPFSK' and (/config_data/main/RadioChannel/RR_RadioModType != 'FSK')) or (. = 'DPSK' and (/config_data/main/RadioChannel/RR_RadioModType != 'QAM')) or (. = 'pi/4DQPSK' and (/config_data/main/RadioChannel/RR_RadioModType != 'QAM')) or (. = 'D8PSK' and (/config_data/main/RadioChannel/RR_RadioModType != 'QAM')) or (. = '16DEQAM' and (/config_data/main/RadioChannel/RR_RadioModType != 'QAM')) or (. = '64QAM' and (/config_data/main/RadioChannel/RR_RadioModType != 'QAM')) or (. = '256QAM' and ((/config_data/main/RadioChannel/RR_RadioModType != 'QAM') or (/config_data/device/DeviceSwKey/RR_SwKey_Flag_radio_modulation_over_64QAM != 'On') or (/config_data/device/DeviceHw/RR_DynHw_Radio_Modulation_Over_64QAM != 'On'))))";
                }
                leaf "RR_RadioFEC" {
                    when "not (((/config_data/main/RadioProtocol/RR_RadioAccessProtocol = 'Base driven') and (/config_data/main/RadioProtocolBaseDr/RR_RadioBDP_StationType = 'Remote')) or ((/config_data/main/RadioChannel/RR_RadioACMEn = 'On') and (/config_data/device/DeviceHw/RR_DynHw_Radio_Acm = 'On')))";
                    type "lbox_radio_fec_M9";
                    must "not ((. = '1/1' and ((/config_data/main/RadioChannel/RR_RadioModulation = '256QAM') and ((/config_data/main/RadioChannel/RR_RadioChSpacing = '250' and /config_data/main/RadioChannel/RR_RadioChSpacing = '300') or ((/config_data/main/RadioChannel/RR_RadioChSpacing = '200') and (/config_data/main/RadioChannel/RR_RadioChOccupied = '200'))))) or (. = '5/6' and (/config_data/main/RadioChannel/RR_RadioModulation != '64QAM' and /config_data/main/RadioChannel/RR_RadioModulation != '256QAM')) or (. = '2/3' and (/config_data/main/RadioChannel/RR_RadioModulation != '64QAM' and /config_data/main/RadioChannel/RR_RadioModulation != '256QAM')))";
                }
                leaf "RR_RadioAntennaDetSens" {
                    when "not (/config_data/device/DeviceHw/RR_DynHw_Radio_AntennaDet != 'On')";
                    type "decimal64" {
                        fraction-digits "2";
                        range "1.0..2.0";
                    }
                }
                leaf "RR_RadioChSpacingDuplexRx" {
                    when "not ((/config_data/device/DeviceHw/RR_DynHw_Radio_Duplex_Separate_Channels != 'On') or (/config_data/main/RadioProtocol/RR_RadioAccessProtocol != 'Transparent') or (/config_data/main/RadioProtocolTrans/RR_RadioTrans_CommMode != 'Full Duplex'))";
                    type "enumeration" {
                        enum "5" {
                            value "9";
                        }
                        enum "6_25" {
                            value "0";
                        }
                        enum "12_5" {
                            value "1";
                        }
                        enum "25" {
                            value "2";
                        }
                        enum "50" {
                            value "3";
                        }
                        enum "100" {
                            value "4";
                        }
                        enum "150" {
                            value "5";
                        }
                        enum "200" {
                            value "6";
                        }
                        enum "250" {
                            value "7";
                        }
                        enum "300" {
                            value "8";
                        }
                        enum "400" {
                            value "10";
                        }
                        enum "625" {
                            value "11";
                        }
                        enum "1250" {
                            value "12";
                        }
                        enum "2500" {
                            value "13";
                        }
                        enum "5000" {
                            value "14";
                        }
                        enum "10000" {
                            value "15";
                        }
                    }
                    must "not ((. = '5' and (/config_data/region/Region/RR_DynReg_ChSpacing_Val_9_En != 'On')) or (. = '6_25' and (/config_data/region/Region/RR_DynReg_ChSpacing_Val_0_En != 'On')) or (. = '12_5' and (/config_data/region/Region/RR_DynReg_ChSpacing_Val_1_En != 'On')) or (. = '25' and (/config_data/region/Region/RR_DynReg_ChSpacing_Val_2_En != 'On')) or (. = '50' and (/config_data/region/Region/RR_DynReg_ChSpacing_Val_3_En != 'On')) or (. = '100' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_4_En != 'On'))) or (. = '150' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_5_En != 'On'))) or (. = '200' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_6_En != 'On'))) or (. = '250' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_7_En != 'On'))) or (. = '300' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_8_En != 'On'))) or (. = '400' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_10_En != 'On'))) or (. = '625' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_11_En != 'On'))) or (. = '1250' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_12_En != 'On'))) or (. = '2500' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_13_En != 'On'))) or (. = '5000' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_14_En != 'On'))) or (. = '10000' and ((/config_data/device/DeviceHw/RR_DynHw_Radio_ChSpacing_Over_50kHz != 'On') or (/config_data/device/DeviceSwKey/RR_SwKey_Flag_radio_chspacing_over_50kHz != 'On') or (/config_data/region/Region/RR_DynReg_ChSpacing_Val_15_En != 'On'))))";
                }
                leaf "RR_RadioChOccupiedDuplexRx" {
                    when "not ((/config_data/device/DeviceHw/RR_DynHw_Radio_Duplex_Separate_Channels != 'On') or (/config_data/main/RadioProtocol/RR_RadioAccessProtocol != 'Transparent') or (/config_data/main/RadioProtocolTrans/RR_RadioTrans_CommMode != 'Full Duplex'))";
                    type "enumeration" {
                        enum "5" {
                            value "0";
                        }
                        enum "6_25" {
                            value "1";
                        }
                        enum "11" {
                            value "2";
                        }
                        enum "12_5" {
                            value "3";
                        }
                        enum "14" {
                            value "18";
                        }
                        enum "16" {
                            value "4";
                        }
                        enum "20" {
                            value "5";
                        }
                        enum "25" {
                            value "6";
                        }
                        enum "40" {
                            value "7";
                        }
                        enum "50" {
                            value "8";
                        }
                        enum "80" {
                            value "9";
                        }
                        enum "100" {
                            value "16";
                        }
                        enum "125" {
                            value "10";
                        }
                        enum "150" {
                            value "17";
                        }
                        enum "175" {
                            value "11";
                        }
                        enum "200" {
                            value "12";
                        }
                        enum "225" {
                            value "13";
                        }
                        enum "250" {
                            value "14";
                        }
                        enum "300" {
                            value "15";
                        }
                        enum "400" {
                            value "19";
                        }
                        enum "625" {
                            value "20";
                        }
                        enum "1250" {
                            value "21";
                        }
                        enum "2500" {
                            value "22";
                        }
                        enum "5000" {
                            value "23";
                        }
                        enum "10000" {
                            value "24";
                        }
                    }
                    must "not ((. = '5' and ((/config_data/main/RadioChannel/RR_RadioChSpacingDuplexRx != '6_25') or (/config_data/region/Region/RR_DynReg_ChOccupied_Val_0_En != 'On'))) or (. = '6_25' and ((/config_data/main/RadioChannel/RR_RadioChSpacingDuplexRx != '6_25') or (/config_data/region/Region/RR_DynReg_ChOccupied_Val_1_En != 'On'))) or (. = '11' and ((/config_data/main/RadioChannel/RR_RadioChSpacingDuplexRx != '12_5') or (/config_data/region/Region/RR_DynReg_ChOccupied_Val_2_En != 'On'))) or (. = '12_5' and ((/config_data/main/RadioChannel/RR_RadioChSpacingDuplexRx != '12_5') or (/config_data/region/Region/RR_DynReg_ChOccupied_Val_3_En != 'On'))) or (. = '14' and ((/config_data/main/RadioChannel/RR_RadioChSpacingDuplexRx != '25') or (/config_data/region/Region/RR_DynReg_ChOccupied_Val_18_En != 'On'))) or (. = '16' and ((/config_data/main/RadioChannel/RR_RadioChSpacingDuplexRx != '25') or (/config_data/region/Region/RR_DynReg_ChOccupied_Val_4_En != 'On'))) or (. = '20' and ((/config_data/main/RadioChannel/RR_RadioChSpacingDuplexRx != '25') or (/config_data/region/Region/RR_DynReg_ChOccupied_Val_5_En != 'On'))) or (. = '25' and ((/config_data/main/RadioChannel/RR_RadioChSpacingDuplexRx != '25') or (/config_data/region/Region/RR_DynReg_ChOccupied_Val_6_En != 'On'))) or (. = '40' and ((/config_data/main/RadioChannel/RR_RadioChSpacingDuplexRx != '50') or (/config_data/region/Region/RR_DynReg_ChOccupied_Val_7_En != 'On'))) or (. = '50' and ((/config_data/main/RadioChannel/RR_RadioChSpacingDuplexRx != '50') or (/config_data/region/Region/RR_DynReg_ChOccupied_Val_8_En != 'On'))) or (. = '80' and ((/config_data/main/RadioChannel/RR_RadioChSpacingDuplexRx != '100') or (/config_data/region/Region/RR_DynReg_ChOccupied_Val_9_En != 'On'))) or (. = '100' and ((/config_data/main/RadioChannel/RR_RadioChSpacingDuplexRx != '100') or (/config_data/region/Region/RR_DynReg_ChOccupied_Val_16_En != 'On'))) or (. = '125' and ((/config_data/main/RadioChannel/RR_RadioChSpacingDuplexRx != '150') or (/config_data/region/Region/RR_DynReg_ChOccupied_Val_10_En != 'On'))) or (. = '150' and ((/config_data/main/RadioChannel/RR_RadioChSpacingDuplexRx != '150') or (/config_data/region/Region/RR_DynReg_ChOccupied_Val_17_En != 'On'))) or (. = '175' and ((/config_data/main/RadioChannel/RR_RadioChSpacingDuplexRx != '200') or (/config_data/region/Region/RR_DynReg_ChOccupied_Val_11_En != 'On'))) or (. = '200' and ((/config_data/main/RadioChannel/RR_RadioChSpacingDuplexRx != '200') or (/config_data/region/Region/RR_DynReg_ChOccupied_Val_12_En != 'On'))) or (. = '225' and ((/config_data/main/RadioChannel/RR_RadioChSpacingDuplexRx != '250') or (/config_data/region/Region/RR_DynReg_ChOccupied_Val_13_En != 'On'))) or (. = '250' and ((/config_data/main/RadioChannel/RR_RadioChSpacingDuplexRx != '250') or (/config_data/region/Region/RR_DynReg_ChOccupied_Val_14_En != 'On'))) or (. = '300' and ((/config_data/main/RadioChannel/RR_RadioChSpacingDuplexRx != '300') or (/config_data/region/Region/RR_DynReg_ChOccupied_Val_15_En != 'On'))) or (. = '400' and ((/config_data/main/RadioChannel/RR_RadioChSpacingDuplexRx != '400') or (/config_data/region/Region/RR_DynReg_ChOccupied_Val_19_En != 'On'))) or (. = '625' and ((/config_data/main/RadioChannel/RR_RadioChSpacingDuplexRx != '625') or (/config_data/region/Region/RR_DynReg_ChOccupied_Val_20_En != 'On'))) or (. = '1250' and ((/config_data/main/RadioChannel/RR_RadioChSpacingDuplexRx != '1250') or (/config_data/region/Region/RR_DynReg_ChOccupied_Val_21_En != 'On'))) or (. = '2500' and ((/config_data/main/RadioChannel/RR_RadioChSpacingDuplexRx != '2500') or (/config_data/region/Region/RR_DynReg_ChOccupied_Val_22_En != 'On'))) or (. = '5000' and ((/config_data/main/RadioChannel/RR_RadioChSpacingDuplexRx != '5000') or (/config_data/region/Region/RR_DynReg_ChOccupied_Val_23_En != 'On'))) or (. = '10000' and ((/config_data/main/RadioChannel/RR_RadioChSpacingDuplexRx != '10000') or (/config_data/region/Region/RR_DynReg_ChOccupied_Val_24_En != 'On'))))";
                }
            }
            container "RadioACM" {
                when "not ((/config_data/device/DeviceHw/RR_DynHw_Primary_Radio != 'On') or (/config_data/device/DeviceHw/RR_DynHw_Radio_Acm != 'On') or (/config_data/main/RadioChannel/RR_RadioACMEn != 'On') or (/config_data/main/RadioProtocol/RR_RadioAccessProtocol = 'None'))";
                leaf "RR_RadioACMDefaultProfile" {
                    when "not ((/config_data/main/RadioProtocol/RR_RadioAccessProtocol = 'Base driven') and (/config_data/main/RadioProtocolBaseDr/RR_RadioBDP_StationType != 'Base'))";
                    type "lbox_radio_acm_profiles_M1";
                    must "not ((. = 'LB_radio_acm_profiles_2CPFSK_3_4' and (/config_data/main/RadioChannel/RR_RadioModType != 'FSK')) or (. = 'LB_radio_acm_profiles_4CPFSK_3_4' and (/config_data/main/RadioChannel/RR_RadioModType != 'FSK')) or (. = 'LB_radio_acm_profiles_4CPFSK_1_1' and (/config_data/main/RadioChannel/RR_RadioModType != 'FSK')) or (. = 'LB_radio_acm_profiles_DPSK_3_4' and (/config_data/main/RadioChannel/RR_RadioModType != 'QAM')) or (. = 'LB_radio_acm_profiles_pi4DQPSK_3_4' and (/config_data/main/RadioChannel/RR_RadioModType != 'QAM')) or (. = 'LB_radio_acm_profiles_16DEQAM_3_4' and (/config_data/main/RadioChannel/RR_RadioModType != 'QAM')) or (. = 'LB_radio_acm_profiles_64QAM_3_4' and (/config_data/main/RadioChannel/RR_RadioModType != 'QAM')) or (. = 'LB_radio_acm_profiles_256QAM_3_4' and ((/config_data/main/RadioChannel/RR_RadioModType != 'QAM') or (/config_data/device/DeviceSwKey/RR_SwKey_Flag_radio_modulation_over_64QAM != 'On') or (/config_data/device/DeviceHw/RR_DynHw_Radio_Modulation_Over_64QAM != 'On'))) or (. = 'LB_radio_acm_profiles_256QAM_5_6' and ((/config_data/main/RadioChannel/RR_RadioModType != 'QAM') or (/config_data/device/DeviceSwKey/RR_SwKey_Flag_radio_modulation_over_64QAM != 'On') or (/config_data/device/DeviceHw/RR_DynHw_Radio_Modulation_Over_64QAM != 'On'))))";
                }
                leaf "RR_RadioACMBestProfile" {
                    when "not ((/config_data/main/RadioProtocol/RR_RadioAccessProtocol = 'Base driven') and (/config_data/main/RadioProtocolBaseDr/RR_RadioBDP_StationType != 'Base'))";
                    type "lbox_radio_acm_profiles_M1";
                    must "not ((. = 'LB_radio_acm_profiles_2CPFSK_3_4' and (/config_data/main/RadioChannel/RR_RadioModType != 'FSK')) or (. = 'LB_radio_acm_profiles_4CPFSK_3_4' and (/config_data/main/RadioChannel/RR_RadioModType != 'FSK')) or (. = 'LB_radio_acm_profiles_4CPFSK_1_1' and (/config_data/main/RadioChannel/RR_RadioModType != 'FSK')) or (. = 'LB_radio_acm_profiles_DPSK_3_4' and (/config_data/main/RadioChannel/RR_RadioModType != 'QAM')) or (. = 'LB_radio_acm_profiles_pi4DQPSK_3_4' and (/config_data/main/RadioChannel/RR_RadioModType != 'QAM')) or (. = 'LB_radio_acm_profiles_16DEQAM_3_4' and (/config_data/main/RadioChannel/RR_RadioModType != 'QAM')) or (. = 'LB_radio_acm_profiles_64QAM_3_4' and (/config_data/main/RadioChannel/RR_RadioModType != 'QAM')) or (. = 'LB_radio_acm_profiles_256QAM_3_4' and ((/config_data/main/RadioChannel/RR_RadioModType != 'QAM') or (/config_data/device/DeviceSwKey/RR_SwKey_Flag_radio_modulation_over_64QAM != 'On') or (/config_data/device/DeviceHw/RR_DynHw_Radio_Modulation_Over_64QAM != 'On'))) or (. = 'LB_radio_acm_profiles_256QAM_5_6' and ((/config_data/main/RadioChannel/RR_RadioModType != 'QAM') or (/config_data/device/DeviceSwKey/RR_SwKey_Flag_radio_modulation_over_64QAM != 'On') or (/config_data/device/DeviceHw/RR_DynHw_Radio_Modulation_Over_64QAM != 'On'))))";
                }
                leaf "RR_RadioACMReplyTimeout" {
                    type "uint8" {
                        range "1..60";
                    }
                }
                leaf "RR_RadioACMFallbackTimeout" {
                    when "not ((/config_data/main/RadioProtocol/RR_RadioAccessProtocol = 'Base driven') and (/config_data/main/RadioProtocolBaseDr/RR_RadioBDP_StationType != 'Base'))";
                    type "uint8" {
                        range "1..60";
                    }
                }
                leaf "RR_RadioACMMeasTimeConst" {
                    type "uint16" {
                        range "1..300";
                    }
                }
                leaf "RR_RadioACMBlockTimeStart" {
                    when "not ((/config_data/main/RadioProtocol/RR_RadioAccessProtocol = 'Base driven') and (/config_data/main/RadioProtocolBaseDr/RR_RadioBDP_StationType != 'Base'))";
                    type "uint16" {
                        range "1..1440";
                    }
                    must ". <= /config_data/main/RadioACM/RR_RadioACMBlockTimeMax" {
                        error-message "valmsg_it_RadioACMBlockTimeStart";
                    }
                }
                leaf "RR_RadioACMBlockTimeMax" {
                    when "not ((/config_data/main/RadioProtocol/RR_RadioAccessProtocol = 'Base driven') and (/config_data/main/RadioProtocolBaseDr/RR_RadioBDP_StationType != 'Base'))";
                    type "uint16" {
                        range "1..1440";
                    }
                    must ". >= /config_data/main/RadioACM/RR_RadioACMBlockTimeStart" {
                        error-message "valmsg_it_RadioACMBlockTimeMax";
                    }
                }
            }
            container "RadioProtocol" {
                when "not (/config_data/device/DeviceHw/RR_DynHw_Primary_Radio != 'On')";
                leaf "RR_RadioAccessProtocol" {
                    type "enumeration" {
                        enum "Transparent" {
                            value "0";
                        }
                        enum "Flexible" {
                            value "1";
                        }
                        enum "Base driven" {
                            value "2";
                        }
                        enum "None" {
                            value "3";
                        }
                    }
                    must "not ((. = 'Transparent' and (/config_data/main/RadioInterface/RR_RadioIfMode != 'Bridge')) or (. = 'Flexible' and ((/config_data/device/DeviceSwKey/RR_SwKey_Flag_radio_protocols != 'On') or (/config_data/main/RadioInterface/RR_RadioIfMode != 'Router'))) or (. = 'Base driven' and ((/config_data/device/DeviceHw/RR_DynHw_Radio_Protocol_Bdp != 'On') or (/config_data/device/DeviceSwKey/RR_SwKey_Flag_radio_protocols != 'On') or (/config_data/main/RadioInterface/RR_RadioIfMode != 'Router'))))";
                }
                leaf "RR_RadioCompression" {
                    type "enumeration" {
                        enum "Off" {
                            value "0";
                        }
                        enum "LZO" {
                            value "1";
                        }
                    }
                }
                leaf "RR_RadioAck" {
                    when "not ((/config_data/main/RadioProtocol/RR_RadioAccessProtocol = 'Transparent' and /config_data/main/RadioProtocol/RR_RadioAccessProtocol = 'None') or ((/config_data/main/RadioProtocol/RR_RadioAccessProtocol = 'Base driven') and (/config_data/main/RadioProtocolBaseDr/RR_RadioBDP_StationType = 'Base')))";
                    type "lbox_off_on";
                }
                leaf "RR_RadioRetries" {
                    when "not ((/config_data/main/RadioProtocol/RR_RadioAccessProtocol = 'Transparent' and /config_data/main/RadioProtocol/RR_RadioAccessProtocol = 'None') or ((/config_data/main/RadioProtocol/RR_RadioAccessProtocol = 'Base driven') and (/config_data/main/RadioProtocolBaseDr/RR_RadioBDP_StationType = 'Base')) or (/config_data/main/RadioProtocol/RR_RadioAck != 'On'))";
                    type "lim_radio_retries";
                }
                leaf "RR_RadioEncryption" {
                    type "enumeration" {
                        enum "Off" {
                            value "0";
                        }
                        enum "AES-256-CCM" {
                            value "1";
                        }
                        enum "AES-256-CCM + KEX" {
                            value "2";
                        }
                    }
                    must "not ((. = 'AES-256-CCM' and (/config_data/device/DeviceHw/RR_DynHw_NoCrypt = 'On')) or (. = 'AES-256-CCM + KEX' and (/config_data/device/DeviceHw/RR_DynHw_NoCrypt = 'On')))";
                }
            }
            container "RadioProtocolTrans" {
                when "not ((/config_data/device/DeviceHw/RR_DynHw_Primary_Radio != 'On') or (/config_data/main/RadioProtocol/RR_RadioAccessProtocol != 'Transparent'))";
                leaf "RR_RadioTrans_Repeater" {
                    when "not ((/config_data/main/RadioChannel/RR_RadioACMEn = 'On') and (/config_data/device/DeviceHw/RR_DynHw_Radio_Acm = 'On'))";
                    type "lbox_off_on";
                }
                leaf "RR_RadioTrans_RepsNo" {
                    when "not ((/config_data/main/RadioChannel/RR_RadioACMEn = 'On') and (/config_data/device/DeviceHw/RR_DynHw_Radio_Acm = 'On'))";
                    type "uint8" {
                        range "0..7";
                    }
                }
                leaf "RR_RadioTrans_CommMode" {
                    type "enumeration" {
                        enum "Half Duplex" {
                            value "0";
                        }
                        enum "Full Duplex" {
                            value "1";
                        }
                    }
                    must "not ((. = 'Full Duplex' and ((/config_data/device/DeviceHw/RR_DynHw_Radio_Antenna_Dual != 'On') or (/config_data/device/DeviceSwKey/RR_SwKey_Flag_radio_full_duplex != 'On'))))";
                }
                leaf "RR_RadioTrans_TxDelay" {
                    type "uint16" {
                        range "0..16000";
                    }
                }
            }
            container "RadioProtocolBaseDr" {
                when "not ((/config_data/device/DeviceHw/RR_DynHw_Primary_Radio != 'On') or (/config_data/main/RadioProtocol/RR_RadioAccessProtocol != 'Base driven'))";
                leaf "RR_RadioBDP_StationType" {
                    type "enumeration" {
                        enum "Remote" {
                            value "0";
                        }
                        enum "Base" {
                            value "1";
                        }
                    }
                    must "not ((. = 'Base' and (/config_data/device/DeviceHw/RR_DynHw_Radio_Protocol_Bdp_Base != 'On')))";
                }
                leaf "RR_RadioBDP_AutoAddress" {
                    when "not (/config_data/main/RadioProtocolBaseDr/RR_RadioBDP_StationType != 'Remote')";
                    type "lbox_off_on";
                }
                leaf "RR_RadioBDP_Address" {
                    when "not ((/config_data/main/RadioProtocolBaseDr/RR_RadioBDP_StationType != 'Remote') or (/config_data/main/RadioProtocolBaseDr/RR_RadioBDP_AutoAddress = 'On'))";
                    type "lim_uint_8";
                }
                leaf "RR_RadioBDP_BurstSize" {
                    when "not (/config_data/main/RadioProtocolBaseDr/RR_RadioBDP_StationType != 'Base')";
                    type "uint8" {
                        range "0..15";
                    }
                }
                leaf "RR_RadioBDP_BcastRepeats" {
                    when "not (/config_data/main/RadioProtocolBaseDr/RR_RadioBDP_StationType != 'Base')";
                    type "uint8" {
                        range "0..15";
                    }
                }
                leaf "RR_RadioBDP_QueryTimeout" {
                    when "not (/config_data/main/RadioProtocolBaseDr/RR_RadioBDP_StationType != 'Base')";
                    type "decimal64" {
                        fraction-digits "2";
                        range "0.01..30.0";
                    }
                }
            }
            container "RadioProtocolFlexible" {
                when "not ((/config_data/device/DeviceHw/RR_DynHw_Primary_Radio != 'On') or (/config_data/main/RadioProtocol/RR_RadioAccessProtocol != 'Flexible'))";
                leaf "RR_RadioFlex_BcastRepeats" {
                    type "lim_radio_retries";
                }
                leaf "RR_RadioFlex_SlotsNo_Rx" {
                    type "uint8" {
                        range "0..12";
                    }
                }
                leaf "RR_RadioFlex_TxDelayBusy_Len" {
                    type "uint16" {
                        range "0..16000";
                    }
                }
                leaf "RR_RadioFlex_TxDelayFree_Prob" {
                    type "uint8" {
                        range "0..100";
                    }
                }
                leaf "RR_RadioFlex_TxDelayFree_Len" {
                    when "not (/config_data/main/RadioProtocolFlexible/RR_RadioFlex_TxDelayFree_Prob = 0)";
                    type "uint16" {
                        range "1..16000";
                    }
                }
                leaf "RR_RadioFlex_RssThold" {
                    type "uint8" {
                        range "50..150";
                    }
                }
                leaf "RR_RadioFlex_SlotLen" {
                    type "uint8" {
                        range "0..250";
                    }
                }
                leaf "RR_RadioFlex_SlotsNo_Tx" {
                    type "uint8" {
                        range "0..12";
                    }
                }
                leaf "RR_RadioFlex_SlotsNo_Add" {
                    type "uint8" {
                        range "0..7";
                    }
                }
                leaf "RR_RadioFlex_RetrTout_VarNo" {
                    type "uint8" {
                        range "0..15";
                    }
                }
                leaf "RR_RadioFlex_RetrTout_Progressive" {
                    type "lbox_off_on";
                }
                leaf "RR_RadioFlex_ComBcastRep_En" {
                    type "lbox_off_on";
                }
                leaf "RR_RadioFlex_ComBcastRep_DelayMode" {
                    when "not (/config_data/main/RadioProtocolFlexible/RR_RadioFlex_ComBcastRep_En = 'Off')";
                    type "enumeration" {
                        enum "Random" {
                            value "0";
                        }
                        enum "Fixed" {
                            value "1";
                        }
                    }
                }
                leaf "RR_RadioFlex_RetrTout_FixLen" {
                    type "uint16" {
                        range "10..10000";
                    }
                }
                leaf "RR_RadioFlex_RetrTout_VarLen" {
                    when "not (/config_data/main/RadioProtocolFlexible/RR_RadioFlex_RetrTout_VarNo = 0)";
                    type "uint16" {
                        range "10..10000";
                    }
                }
                leaf "RR_RadioFlex_ComBcastRep_DelaySlots" {
                    when "not (/config_data/main/RadioProtocolFlexible/RR_RadioFlex_ComBcastRep_En = 'Off')";
                    type "uint8" {
                        range "0..15";
                    }
                }
            }
            container "RadioEncryption" {
                when "not ((/config_data/device/DeviceHw/RR_DynHw_Primary_Radio != 'On') or (/config_data/main/RadioProtocol/RR_RadioEncryption = 'Off'))";
                leaf "RR_RadioEncr_KeyMode" {
                    type "lbox_psk_key_mode";
                }
                leaf "RR_RadioEncr_Key2Mode" {
                    type "lbox_psk_key_mode";
                }
                leaf "RR_RadioEncr_KeyId" {
                    when "not (/config_data/main/RadioEncryption/RR_RadioEncr_KeyMode != 'Key')";
                    type "string" {
                        pattern "[a-zA-Z0-9_]{0,128}";
                    }
                }
                leaf "RR_RadioEncr_PassPhrase" {
                    when "not (/config_data/main/RadioEncryption/RR_RadioEncr_KeyMode != 'Pass Phrase')";
                    type "string" {
                        pattern "[^\"`\\\\$;]{0,128}";
                    }
                }
                leaf "RR_RadioEncr_Key2Id" {
                    when "not (/config_data/main/RadioEncryption/RR_RadioEncr_Key2Mode != 'Key')";
                    type "string" {
                        pattern "[a-zA-Z0-9_]{0,128}";
                    }
                }
                leaf "RR_RadioEncr_PassPhrase2" {
                    when "not (/config_data/main/RadioEncryption/RR_RadioEncr_Key2Mode != 'Pass Phrase')";
                    type "string" {
                        pattern "[^\"`\\\\$;]{0,128}";
                    }
                }
                leaf "RR_RadioEncr_RekeyPeriod" {
                    when "not (/config_data/main/RadioProtocol/RR_RadioEncryption != 'AES-256-CCM + KEX')";
                    type "uint16" {
                        range "5..10080";
                    }
                }
            }
            container "RadioProtocolQueues" {
                when "not ((/config_data/device/DeviceHw/RR_DynHw_Primary_Radio != 'On') or (/config_data/main/RadioProtocol/RR_RadioAccessProtocol = 'None'))";
                leaf "RR_RadioQ_TxBufStoreToutEnable" {
                    type "lbox_off_on";
                }
                leaf "RR_RadioQ_QueueLen" {
                    type "uint8" {
                        range "1..31";
                    }
                }
                leaf "RR_RadioQ_TxBufStoreTout" {
                    when "not (/config_data/main/RadioProtocolQueues/RR_RadioQ_TxBufStoreToutEnable != 'On')";
                    type "decimal64" {
                        fraction-digits "2";
                        range "0.01..150.0";
                    }
                }
                leaf "RR_RadioQ_QueueSize" {
                    type "uint8" {
                        range "1..48";
                    }
                }
            }
            container "Cellular" {
                leaf "RR_CellMain_Enable" {
                    when "not (/config_data/device/DeviceHw/RR_DynHw_Primary_Cellular != 'On')";
                    type "lbox_off_on";
                }
                leaf "RR_CellAux_Enable" {
                    when "not (/config_data/device/DeviceHw/RR_DynHw_Module_Cellular != 'On')";
                    type "lbox_off_on";
                }
            }
            container "CellularMain" {
                when "not ((/config_data/device/DeviceHw/RR_DynHw_Primary_Cellular != 'On') or (/config_data/main/Cellular/RR_CellMain_Enable != 'On'))";
                leaf "RR_CellMain_Masquerade" {
                    type "lbox_off_on";
                }
                leaf "RR_CellMain_MngEn" {
                    type "lbox_off_on";
                }
                leaf "RR_CellMain_LinkTesting" {
                    type "lbox_off_on";
                }
                leaf "RR_CellMain_ProfileSwitching" {
                    type "lbox_off_on";
                }
                leaf "RR_CellMain_SmsCommands" {
                    when "not (/config_data/device/DeviceHw/RR_DynHw_Cell_Main_Sms != 'On')";
                    type "lbox_off_on";
                }
                leaf "RR_CellMain_SmsNotifications" {
                    when "not (/config_data/device/DeviceHw/RR_DynHw_Cell_Main_Sms != 'On')";
                    type "lbox_off_on";
                }
                leaf "RR_CellMain_RmtAccEn" {
                    when "not (/config_data/main/UserAccess/RR_UsAcc_RmtAccess_Enable != 'On')";
                    type "lbox_off_on";
                }
                leaf "RR_CellMain_CtrlMsgLogEn" {
                    type "lbox_off_on";
                }
            }
            container "CellularMainLinkTester" {
                when "not ((/config_data/device/DeviceHw/RR_DynHw_Primary_Cellular != 'On') or (/config_data/main/Cellular/RR_CellMain_Enable != 'On') or (/config_data/main/CellularMain/RR_CellMain_LinkTesting != 'On'))";
                leaf "RR_CellMainLT_TestPeriod" {
                    type "uint16" {
                        range "3..3600";
                    }
                }
                leaf "RR_CellMainLT_RepeatPeriod" {
                    type "uint16" {
                        range "3..3600";
                    }
                }
                leaf "RR_CellMainLT_WaitTime" {
                    type "uint8" {
                        range "1..60";
                    }
                }
                leaf "RR_CellMainLT_FailCnt" {
                    type "uint8" {
                        range "1..20";
                    }
                }
                leaf "RR_CellMainLT_UseBackupAddr" {
                    type "lbox_off_on";
                }
                leaf "RR_CellMainLT_EvaluationType" {
                    when "not (/config_data/main/CellularMainLinkTester/RR_CellMainLT_UseBackupAddr != 'On')";
                    type "enumeration" {
                        enum "LB_CellLT_ProfileSwitch_One_succeeds" {
                            value "0";
                        }
                        enum "LB_CellLT_ProfileSwitch_Both_succeed" {
                            value "1";
                        }
                    }
                }
                leaf "RR_CellMainLT_TestAddr" {
                    type "string" {
                        pattern "[a-zA-Z0-9.-]{1,128}";
                    }
                }
                leaf "RR_CellMainLT_BackupTestAddr" {
                    when "not (/config_data/main/CellularMainLinkTester/RR_CellMainLT_UseBackupAddr != 'On')";
                    type "string" {
                        pattern "[a-zA-Z0-9.-]{1,128}";
                    }
                }
            }
            container "CellularMainProfileSwitch" {
                when "not ((/config_data/device/DeviceHw/RR_DynHw_Primary_Cellular != 'On') or (/config_data/main/Cellular/RR_CellMain_Enable != 'On') or (/config_data/main/CellularMain/RR_CellMain_ProfileSwitching != 'On'))";
                leaf "RR_CellMainPS_SwitchingMethod" {
                    type "enumeration" {
                        enum "LB_CellPS_SwitchingMethod_First_fail" {
                            value "0";
                        }
                        enum "LB_CellPS_SwitchingMethod_Retry_running" {
                            value "1";
                        }
                        enum "LB_CellPS_SwitchingMethod_Timeout" {
                            value "2";
                        }
                    }
                }
                leaf "RR_CellMainPS_ConnectionTimeout" {
                    type "uint8" {
                        range "3..60";
                    }
                }
                leaf "RR_CellMainPS_RetryFirstProfile" {
                    type "lbox_off_on";
                }
                leaf "RR_CellMainPS_RetryTimeout" {
                    when "not (/config_data/main/CellularMainProfileSwitch/RR_CellMainPS_RetryFirstProfile != 'On')";
                    type "uint16" {
                        range "5..10080";
                    }
                }
            }
            container "CellularAux" {
                when "not ((/config_data/device/DeviceHw/RR_DynHw_Module_Cellular != 'On') or (/config_data/main/Cellular/RR_CellAux_Enable != 'On'))";
                leaf "RR_CellAux_Masquerade" {
                    type "lbox_off_on";
                }
                leaf "RR_CellAux_MngEn" {
                    type "lbox_off_on";
                }
                leaf "RR_CellAux_LinkTesting" {
                    type "lbox_off_on";
                }
                leaf "RR_CellAux_ProfileSwitching" {
                    type "lbox_off_on";
                }
                leaf "RR_CellAux_SmsCommands" {
                    when "not (/config_data/device/DeviceHw/RR_DynHw_Cell_Ext_Sms != 'On')";
                    type "lbox_off_on";
                }
                leaf "RR_CellAux_SmsNotifications" {
                    when "not (/config_data/device/DeviceHw/RR_DynHw_Cell_Ext_Sms != 'On')";
                    type "lbox_off_on";
                }
                leaf "RR_CellAux_RmtAccEn" {
                    when "not (/config_data/main/UserAccess/RR_UsAcc_RmtAccess_Enable != 'On')";
                    type "lbox_off_on";
                }
                leaf "RR_CellAux_CtrlMsgLogEn" {
                    type "lbox_off_on";
                }
            }
            container "CellularAuxLinkTester" {
                when "not ((/config_data/device/DeviceHw/RR_DynHw_Module_Cellular != 'On') or (/config_data/main/Cellular/RR_CellAux_Enable != 'On') or (/config_data/main/CellularAux/RR_CellAux_LinkTesting != 'On'))";
                leaf "RR_CellAuxLT_TestPeriod" {
                    type "uint16" {
                        range "3..3600";
                    }
                }
                leaf "RR_CellAuxLT_RepeatPeriod" {
                    type "uint16" {
                        range "3..3600";
                    }
                }
                leaf "RR_CellAuxLT_WaitTime" {
                    type "uint8" {
                        range "1..60";
                    }
                }
                leaf "RR_CellAuxLT_FailCnt" {
                    type "uint8" {
                        range "1..20";
                    }
                }
                leaf "RR_CellAuxLT_UseBackupAddr" {
                    type "lbox_off_on";
                }
                leaf "RR_CellAuxLT_EvaluationType" {
                    when "not (/config_data/main/CellularAuxLinkTester/RR_CellAuxLT_UseBackupAddr != 'On')";
                    type "enumeration" {
                        enum "LB_CellLT_ProfileSwitch_One_succeeds" {
                            value "0";
                        }
                        enum "LB_CellLT_ProfileSwitch_Both_succeed" {
                            value "1";
                        }
                    }
                }
                leaf "RR_CellAuxLT_TestAddr" {
                    type "string" {
                        pattern "[a-zA-Z0-9.-]{1,128}";
                    }
                }
                leaf "RR_CellAuxLT_BackupTestAddr" {
                    when "not (/config_data/main/CellularAuxLinkTester/RR_CellAuxLT_UseBackupAddr != 'On')";
                    type "string" {
                        pattern "[a-zA-Z0-9.-]{1,128}";
                    }
                }
            }
            container "CellularAuxProfileSwitch" {
                when "not ((/config_data/device/DeviceHw/RR_DynHw_Module_Cellular != 'On') or (/config_data/main/Cellular/RR_CellAux_Enable != 'On') or (/config_data/main/CellularAux/RR_CellAux_ProfileSwitching != 'On'))";
                leaf "RR_CellAuxPS_SwitchingMethod" {
                    type "enumeration" {
                        enum "LB_CellPS_SwitchingMethod_First_fail" {
                            value "0";
                        }
                        enum "LB_CellPS_SwitchingMethod_Retry_running" {
                            value "1";
                        }
                        enum "LB_CellPS_SwitchingMethod_Timeout" {
                            value "2";
                        }
                    }
                }
                leaf "RR_CellAuxPS_ConnectionTimeout" {
                    type "uint8" {
                        range "3..60";
                    }
                }
                leaf "RR_CellAuxPS_RetryFirstProfile" {
                    type "lbox_off_on";
                }
                leaf "RR_CellAuxPS_RetryTimeout" {
                    when "not (/config_data/main/CellularAuxProfileSwitch/RR_CellAuxPS_RetryFirstProfile != 'On')";
                    type "uint16" {
                        range "5..10080";
                    }
                }
            }
            container "CellularSim1" {
                when "not (((/config_data/device/DeviceHw/RR_DynHw_Primary_Cellular != 'On') or (/config_data/main/Cellular/RR_CellMain_Enable != 'On')) and ((/config_data/device/DeviceHw/RR_DynHw_Module_Cellular != 'On') or (/config_data/main/Cellular/RR_CellAux_Enable != 'On')))";
                leaf "RR_CellSim1_PinRequired" {
                    type "lbox_off_on";
                }
                leaf "RR_CellSim1_Pin" {
                    when "not (/config_data/main/CellularSim1/RR_CellSim1_PinRequired != 'On')";
                    type "string" {
                        pattern "[0-9]{4}";
                    }
                }
            }
            container "CellularSim2" {
                when "not (((/config_data/device/DeviceHw/RR_DynHw_Primary_Cellular != 'On') or (/config_data/main/Cellular/RR_CellMain_Enable != 'On')) and ((/config_data/device/DeviceHw/RR_DynHw_Module_Cellular != 'On') or (/config_data/main/Cellular/RR_CellAux_Enable != 'On')))";
                leaf "RR_CellSim2_PinRequired" {
                    type "lbox_off_on";
                }
                leaf "RR_CellSim2_Pin" {
                    when "not (/config_data/main/CellularSim2/RR_CellSim2_PinRequired != 'On')";
                    type "string" {
                        pattern "[0-9]{4}";
                    }
                }
            }
            container "CellularSms" {
                when "not (((/config_data/device/DeviceHw/RR_DynHw_Primary_Cellular != 'On') or (/config_data/device/DeviceHw/RR_DynHw_Cell_Main_Sms != 'On') or (/config_data/main/Cellular/RR_CellMain_Enable != 'On') or ((/config_data/main/CellularMain/RR_CellMain_SmsCommands != 'On') and (/config_data/main/CellularMain/RR_CellMain_SmsNotifications != 'On'))) and ((/config_data/device/DeviceHw/RR_DynHw_Module_Cellular != 'On') or (/config_data/device/DeviceHw/RR_DynHw_Cell_Ext_Sms != 'On') or (/config_data/main/Cellular/RR_CellAux_Enable != 'On') or ((/config_data/main/CellularAux/RR_CellAux_SmsCommands != 'On') and (/config_data/main/CellularAux/RR_CellAux_SmsNotifications != 'On'))))";
                leaf "RR_CellSms_SendBufferLen" {
                    type "uint8" {
                        range "16..128";
                    }
                }
                leaf "RR_CellSms_Password" {
                    when "not (((/config_data/device/DeviceHw/RR_DynHw_Primary_Cellular != 'On') or (/config_data/device/DeviceHw/RR_DynHw_Cell_Main_Sms != 'On') or (/config_data/main/Cellular/RR_CellMain_Enable != 'On') or (/config_data/main/CellularMain/RR_CellMain_SmsCommands != 'On')) and ((/config_data/device/DeviceHw/RR_DynHw_Module_Cellular != 'On') or (/config_data/device/DeviceHw/RR_DynHw_Cell_Ext_Sms != 'On') or (/config_data/main/Cellular/RR_CellAux_Enable != 'On') or (/config_data/main/CellularAux/RR_CellAux_SmsCommands != 'On')))";
                    type "string" {
                        pattern "[^\"`\\\\$; ]{2,16}";
                    }
                }
            }
            container "Wifi" {
                leaf "RR_Wifi_Region" {
                    type "enumeration" {
                        enum "LB_wireless_regdb_None" {
                            value "0";
                        }
                        enum "LB_wireless_regdb_AD" {
                            value "1";
                        }
                        enum "LB_wireless_regdb_AE" {
                            value "2";
                        }
                        enum "LB_wireless_regdb_AF" {
                            value "3";
                        }
                        enum "LB_wireless_regdb_AI" {
                            value "4";
                        }
                        enum "LB_wireless_regdb_AL" {
                            value "5";
                        }
                        enum "LB_wireless_regdb_AM" {
                            value "6";
                        }
                        enum "LB_wireless_regdb_AN" {
                            value "7";
                        }
                        enum "LB_wireless_regdb_AR" {
                            value "8";
                        }
                        enum "LB_wireless_regdb_AS" {
                            value "9";
                        }
                        enum "LB_wireless_regdb_AT" {
                            value "10";
                        }
                        enum "LB_wireless_regdb_AU" {
                            value "11";
                        }
                        enum "LB_wireless_regdb_AW" {
                            value "12";
                        }
                        enum "LB_wireless_regdb_AZ" {
                            value "13";
                        }
                        enum "LB_wireless_regdb_BA" {
                            value "14";
                        }
                        enum "LB_wireless_regdb_BB" {
                            value "15";
                        }
                        enum "LB_wireless_regdb_BD" {
                            value "16";
                        }
                        enum "LB_wireless_regdb_BE" {
                            value "17";
                        }
                        enum "LB_wireless_regdb_BF" {
                            value "18";
                        }
                        enum "LB_wireless_regdb_BG" {
                            value "19";
                        }
                        enum "LB_wireless_regdb_BH" {
                            value "20";
                        }
                        enum "LB_wireless_regdb_BL" {
                            value "21";
                        }
                        enum "LB_wireless_regdb_BM" {
                            value "22";
                        }
                        enum "LB_wireless_regdb_BN" {
                            value "23";
                        }
                        enum "LB_wireless_regdb_BO" {
                            value "24";
                        }
                        enum "LB_wireless_regdb_BR" {
                            value "25";
                        }
                        enum "LB_wireless_regdb_BS" {
                            value "26";
                        }
                        enum "LB_wireless_regdb_BT" {
                            value "27";
                        }
                        enum "LB_wireless_regdb_BZ" {
                            value "28";
                        }
                        enum "LB_wireless_regdb_CA" {
                            value "29";
                        }
                        enum "LB_wireless_regdb_CF" {
                            value "30";
                        }
                        enum "LB_wireless_regdb_CH" {
                            value "31";
                        }
                        enum "LB_wireless_regdb_CI" {
                            value "32";
                        }
                        enum "LB_wireless_regdb_CL" {
                            value "33";
                        }
                        enum "LB_wireless_regdb_CN" {
                            value "34";
                        }
                        enum "LB_wireless_regdb_CO" {
                            value "35";
                        }
                        enum "LB_wireless_regdb_CR" {
                            value "36";
                        }
                        enum "LB_wireless_regdb_CU" {
                            value "37";
                        }
                        enum "LB_wireless_regdb_CX" {
                            value "38";
                        }
                        enum "LB_wireless_regdb_CY" {
                            value "39";
                        }
                        enum "LB_wireless_regdb_CZ" {
                            value "40";
                        }
                        enum "LB_wireless_regdb_DE" {
                            value "41";
                        }
                        enum "LB_wireless_regdb_DK" {
                            value "42";
                        }
                        enum "LB_wireless_regdb_DM" {
                            value "43";
                        }
                        enum "LB_wireless_regdb_DO" {
                            value "44";
                        }
                        enum "LB_wireless_regdb_DZ" {
                            value "45";
                        }
                        enum "LB_wireless_regdb_EC" {
                            value "46";
                        }
                        enum "LB_wireless_regdb_EE" {
                            value "47";
                        }
                        enum "LB_wireless_regdb_EG" {
                            value "48";
                        }
                        enum "LB_wireless_regdb_ES" {
                            value "49";
                        }
                        enum "LB_wireless_regdb_ET" {
                            value "50";
                        }
                        enum "LB_wireless_regdb_FI" {
                            value "51";
                        }
                        enum "LB_wireless_regdb_FM" {
                            value "52";
                        }
                        enum "LB_wireless_regdb_FR" {
                            value "53";
                        }
                        enum "LB_wireless_regdb_GB" {
                            value "54";
                        }
                        enum "LB_wireless_regdb_GD" {
                            value "55";
                        }
                        enum "LB_wireless_regdb_GE" {
                            value "56";
                        }
                        enum "LB_wireless_regdb_GF" {
                            value "57";
                        }
                        enum "LB_wireless_regdb_GH" {
                            value "58";
                        }
                        enum "LB_wireless_regdb_GL" {
                            value "59";
                        }
                        enum "LB_wireless_regdb_GP" {
                            value "60";
                        }
                        enum "LB_wireless_regdb_GR" {
                            value "61";
                        }
                        enum "LB_wireless_regdb_GT" {
                            value "62";
                        }
                        enum "LB_wireless_regdb_GU" {
                            value "63";
                        }
                        enum "LB_wireless_regdb_GY" {
                            value "64";
                        }
                        enum "LB_wireless_regdb_HK" {
                            value "65";
                        }
                        enum "LB_wireless_regdb_HN" {
                            value "66";
                        }
                        enum "LB_wireless_regdb_HR" {
                            value "67";
                        }
                        enum "LB_wireless_regdb_HT" {
                            value "68";
                        }
                        enum "LB_wireless_regdb_HU" {
                            value "69";
                        }
                        enum "LB_wireless_regdb_ID" {
                            value "70";
                        }
                        enum "LB_wireless_regdb_IE" {
                            value "71";
                        }
                        enum "LB_wireless_regdb_IL" {
                            value "72";
                        }
                        enum "LB_wireless_regdb_IN" {
                            value "73";
                        }
                        enum "LB_wireless_regdb_IS" {
                            value "74";
                        }
                        enum "LB_wireless_regdb_IT" {
                            value "75";
                        }
                        enum "LB_wireless_regdb_JM" {
                            value "76";
                        }
                        enum "LB_wireless_regdb_JO" {
                            value "77";
                        }
                        enum "LB_wireless_regdb_JP" {
                            value "78";
                        }
                        enum "LB_wireless_regdb_KE" {
                            value "79";
                        }
                        enum "LB_wireless_regdb_KH" {
                            value "80";
                        }
                        enum "LB_wireless_regdb_KN" {
                            value "81";
                        }
                        enum "LB_wireless_regdb_KR" {
                            value "82";
                        }
                        enum "LB_wireless_regdb_KW" {
                            value "83";
                        }
                        enum "LB_wireless_regdb_KY" {
                            value "84";
                        }
                        enum "LB_wireless_regdb_KZ" {
                            value "85";
                        }
                        enum "LB_wireless_regdb_LB" {
                            value "86";
                        }
                        enum "LB_wireless_regdb_LC" {
                            value "87";
                        }
                        enum "LB_wireless_regdb_LI" {
                            value "88";
                        }
                        enum "LB_wireless_regdb_LK" {
                            value "89";
                        }
                        enum "LB_wireless_regdb_LS" {
                            value "90";
                        }
                        enum "LB_wireless_regdb_LT" {
                            value "91";
                        }
                        enum "LB_wireless_regdb_LU" {
                            value "92";
                        }
                        enum "LB_wireless_regdb_LV" {
                            value "93";
                        }
                        enum "LB_wireless_regdb_MA" {
                            value "94";
                        }
                        enum "LB_wireless_regdb_MC" {
                            value "95";
                        }
                        enum "LB_wireless_regdb_MD" {
                            value "96";
                        }
                        enum "LB_wireless_regdb_ME" {
                            value "97";
                        }
                        enum "LB_wireless_regdb_MF" {
                            value "98";
                        }
                        enum "LB_wireless_regdb_MH" {
                            value "99";
                        }
                        enum "LB_wireless_regdb_MK" {
                            value "100";
                        }
                        enum "LB_wireless_regdb_MN" {
                            value "101";
                        }
                        enum "LB_wireless_regdb_MO" {
                            value "102";
                        }
                        enum "LB_wireless_regdb_MP" {
                            value "103";
                        }
                        enum "LB_wireless_regdb_MQ" {
                            value "104";
                        }
                        enum "LB_wireless_regdb_MR" {
                            value "105";
                        }
                        enum "LB_wireless_regdb_MT" {
                            value "106";
                        }
                        enum "LB_wireless_regdb_MU" {
                            value "107";
                        }
                        enum "LB_wireless_regdb_MV" {
                            value "108";
                        }
                        enum "LB_wireless_regdb_MW" {
                            value "109";
                        }
                        enum "LB_wireless_regdb_MX" {
                            value "110";
                        }
                        enum "LB_wireless_regdb_MY" {
                            value "111";
                        }
                        enum "LB_wireless_regdb_NG" {
                            value "112";
                        }
                        enum "LB_wireless_regdb_NI" {
                            value "113";
                        }
                        enum "LB_wireless_regdb_NL" {
                            value "114";
                        }
                        enum "LB_wireless_regdb_NO" {
                            value "115";
                        }
                        enum "LB_wireless_regdb_NP" {
                            value "116";
                        }
                        enum "LB_wireless_regdb_NZ" {
                            value "117";
                        }
                        enum "LB_wireless_regdb_OM" {
                            value "118";
                        }
                        enum "LB_wireless_regdb_PA" {
                            value "119";
                        }
                        enum "LB_wireless_regdb_PE" {
                            value "120";
                        }
                        enum "LB_wireless_regdb_PF" {
                            value "121";
                        }
                        enum "LB_wireless_regdb_PG" {
                            value "122";
                        }
                        enum "LB_wireless_regdb_PH" {
                            value "123";
                        }
                        enum "LB_wireless_regdb_PK" {
                            value "124";
                        }
                        enum "LB_wireless_regdb_PL" {
                            value "125";
                        }
                        enum "LB_wireless_regdb_PM" {
                            value "126";
                        }
                        enum "LB_wireless_regdb_PR" {
                            value "127";
                        }
                        enum "LB_wireless_regdb_PT" {
                            value "128";
                        }
                        enum "LB_wireless_regdb_PW" {
                            value "129";
                        }
                        enum "LB_wireless_regdb_PY" {
                            value "130";
                        }
                        enum "LB_wireless_regdb_QA" {
                            value "131";
                        }
                        enum "LB_wireless_regdb_RE" {
                            value "132";
                        }
                        enum "LB_wireless_regdb_RO" {
                            value "133";
                        }
                        enum "LB_wireless_regdb_RS" {
                            value "134";
                        }
                        enum "LB_wireless_regdb_RW" {
                            value "135";
                        }
                        enum "LB_wireless_regdb_SA" {
                            value "136";
                        }
                        enum "LB_wireless_regdb_SE" {
                            value "137";
                        }
                        enum "LB_wireless_regdb_SG" {
                            value "138";
                        }
                        enum "LB_wireless_regdb_SI" {
                            value "139";
                        }
                        enum "LB_wireless_regdb_SK" {
                            value "140";
                        }
                        enum "LB_wireless_regdb_SN" {
                            value "141";
                        }
                        enum "LB_wireless_regdb_SR" {
                            value "142";
                        }
                        enum "LB_wireless_regdb_SV" {
                            value "143";
                        }
                        enum "LB_wireless_regdb_TC" {
                            value "144";
                        }
                        enum "LB_wireless_regdb_TD" {
                            value "145";
                        }
                        enum "LB_wireless_regdb_TG" {
                            value "146";
                        }
                        enum "LB_wireless_regdb_TH" {
                            value "147";
                        }
                        enum "LB_wireless_regdb_TN" {
                            value "148";
                        }
                        enum "LB_wireless_regdb_TR" {
                            value "149";
                        }
                        enum "LB_wireless_regdb_TT" {
                            value "150";
                        }
                        enum "LB_wireless_regdb_TW" {
                            value "151";
                        }
                        enum "LB_wireless_regdb_TZ" {
                            value "152";
                        }
                        enum "LB_wireless_regdb_UA" {
                            value "153";
                        }
                        enum "LB_wireless_regdb_UG" {
                            value "154";
                        }
                        enum "LB_wireless_regdb_US" {
                            value "155";
                        }
                        enum "LB_wireless_regdb_UY" {
                            value "156";
                        }
                        enum "LB_wireless_regdb_UZ" {
                            value "157";
                        }
                        enum "LB_wireless_regdb_VC" {
                            value "158";
                        }
                        enum "LB_wireless_regdb_VE" {
                            value "159";
                        }
                        enum "LB_wireless_regdb_VI" {
                            value "160";
                        }
                        enum "LB_wireless_regdb_VN" {
                            value "161";
                        }
                        enum "LB_wireless_regdb_VU" {
                            value "162";
                        }
                        enum "LB_wireless_regdb_WF" {
                            value "163";
                        }
                        enum "LB_wireless_regdb_WS" {
                            value "164";
                        }
                        enum "LB_wireless_regdb_YE" {
                            value "165";
                        }
                        enum "LB_wireless_regdb_YT" {
                            value "166";
                        }
                        enum "LB_wireless_regdb_ZA" {
                            value "167";
                        }
                        enum "LB_wireless_regdb_ZW" {
                            value "168";
                        }
                    }
                }
                leaf "RR_WifiExt_Enable" {
                    when "not (/config_data/device/DeviceHw/RR_DynHw_Module_Wifi != 'On')";
                    type "lbox_off_on";
                }
            }
            container "WifiExt" {
                when "not ((/config_data/device/DeviceHw/RR_DynHw_Module_Wifi != 'On') or (/config_data/main/Wifi/RR_WifiExt_Enable != 'On'))";
                leaf "RR_WifiExt_IpAddr" {
                    type "inet:ipv4-address";
                }
                leaf "RR_WifiExt_Netmask" {
                    type "lim_ipv4_mask";
                }
                leaf "RR_WifiExt_MngEn" {
                    type "lbox_off_on";
                }
                leaf "RR_WifiExt_OperationType" {
                    type "enumeration" {
                        enum "LB_wifi_operation_type_Ap" {
                            value "0";
                        }
                        enum "LB_wifi_operation_type_Client" {
                            value "1";
                        }
                    }
                    must "not ((. = 'LB_wifi_operation_type_Client' and (/config_data/auth/CnfAuth/RR_CnfAuthCnfVersion >= 0)))";
                }
                leaf "RR_WifiExt_AutoSsid" {
                    when "not (/config_data/main/WifiExt/RR_WifiExt_OperationType != 'LB_wifi_operation_type_Ap')";
                    type "lbox_off_on";
                }
                leaf "RR_WifiExt_MacAcl" {
                    when "not (/config_data/main/WifiExt/RR_WifiExt_OperationType != 'LB_wifi_operation_type_Ap')";
                    type "lbox_wifi_mac_acl";
                }
                leaf "RR_WifiExt_RmtAccEn" {
                    when "not (/config_data/main/UserAccess/RR_UsAcc_RmtAccess_Enable != 'On')";
                    type "lbox_off_on";
                }
                leaf "RR_WifiExt_HideSsid" {
                    when "not (/config_data/main/WifiExt/RR_WifiExt_OperationType != 'LB_wifi_operation_type_Ap')";
                    type "lbox_off_on";
                }
                leaf "RR_WifiExt_Ssid" {
                    when "not (/config_data/main/WifiExt/RR_WifiExt_AutoSsid != 'Off')";
                    type "string" {
                        pattern "[^\"`\\\\$;]{1,32}";
                    }
                }
                leaf "RR_WifiExt_Password" {
                    when "not (/config_data/main/WifiExt/RR_WifiExt_Security = 'LB_wifi_security_Off')";
                    type "string" {
                        pattern "[^\"`\\\\$;]{0,63}";
                    }
                }
                leaf "RR_WifiExt_Security" {
                    type "lbox_wifi_security";
                }
                leaf "RR_WifiExt_Encryption" {
                    when "not (/config_data/main/WifiExt/RR_WifiExt_Security = 'LB_wifi_security_Off')";
                    type "enumeration" {
                        enum "LB_wifi_ext_encryption_Tkip" {
                            value "0";
                        }
                        enum "LB_wifi_ext_encryption_Aes" {
                            value "1";
                        }
                        enum "LB_wifi_ext_encryption_TkipAes" {
                            value "2";
                        }
                    }
                    must "not ((. = 'LB_wifi_ext_encryption_Tkip' and ((/config_data/main/WifiExt/RR_WifiExt_Security = 'LB_wifi_security_Wpa3') or (/config_data/main/WifiExt/RR_WifiExt_Mode = 'LB_wifi_ext_mode_80211bgn') or (/config_data/main/WifiExt/RR_WifiExt_Mode = 'LB_wifi_ext_mode_80211an') or (/config_data/main/WifiExt/RR_WifiExt_Mode = 'LB_wifi_ext_mode_80211anac'))) or (. = 'LB_wifi_ext_encryption_TkipAes' and ((/config_data/main/WifiExt/RR_WifiExt_Security = 'LB_wifi_security_Wpa3') or (/config_data/main/WifiExt/RR_WifiExt_Mode = 'LB_wifi_ext_mode_80211bgn') or (/config_data/main/WifiExt/RR_WifiExt_Mode = 'LB_wifi_ext_mode_80211an') or (/config_data/main/WifiExt/RR_WifiExt_Mode = 'LB_wifi_ext_mode_80211anac'))))";
                }
                leaf "RR_WifiExt_Mode" {
                    type "enumeration" {
                        enum "LB_wifi_ext_mode_80211a" {
                            value "0";
                        }
                        enum "LB_wifi_ext_mode_80211b" {
                            value "1";
                        }
                        enum "LB_wifi_ext_mode_80211bg" {
                            value "2";
                        }
                        enum "LB_wifi_ext_mode_80211bgn" {
                            value "3";
                        }
                        enum "LB_wifi_ext_mode_80211an" {
                            value "4";
                        }
                        enum "LB_wifi_ext_mode_80211anac" {
                            value "5";
                        }
                    }
                    must "not ((. = 'LB_wifi_ext_mode_80211a' and (/config_data/device/DeviceHw/RR_DynHw_Wifi_Ext_80211a != 'On')) or (. = 'LB_wifi_ext_mode_80211b' and (/config_data/device/DeviceHw/RR_DynHw_Wifi_Ext_80211b != 'On')) or (. = 'LB_wifi_ext_mode_80211bg' and ((/config_data/device/DeviceHw/RR_DynHw_Wifi_Ext_80211b != 'On') or (/config_data/device/DeviceHw/RR_DynHw_Wifi_Ext_80211g != 'On'))) or (. = 'LB_wifi_ext_mode_80211bgn' and ((/config_data/device/DeviceHw/RR_DynHw_Wifi_Ext_80211b != 'On') or (/config_data/device/DeviceHw/RR_DynHw_Wifi_Ext_80211g != 'On') or (/config_data/device/DeviceHw/RR_DynHw_Wifi_Ext_80211n != 'On'))) or (. = 'LB_wifi_ext_mode_80211an' and ((/config_data/device/DeviceHw/RR_DynHw_Wifi_Ext_80211a != 'On') or (/config_data/device/DeviceHw/RR_DynHw_Wifi_Ext_80211n != 'On'))) or (. = 'LB_wifi_ext_mode_80211anac' and ((/config_data/device/DeviceHw/RR_DynHw_Wifi_Ext_80211a != 'On') or (/config_data/device/DeviceHw/RR_DynHw_Wifi_Ext_80211n != 'On') or (/config_data/device/DeviceHw/RR_DynHw_Wifi_Ext_80211ac != 'On'))))";
                }
                leaf "RR_WifiExt_Band" {
                    type "enumeration" {
                        enum "LB_wifi_ext_band_24GHz" {
                            value "0";
                        }
                        enum "LB_wifi_ext_band_5GHz" {
                            value "1";
                        }
                    }
                    must "not ((. = 'LB_wifi_ext_band_24GHz' and ((/config_data/main/WifiExt/RR_WifiExt_Mode != 'LB_wifi_ext_mode_80211b') and (/config_data/main/WifiExt/RR_WifiExt_Mode != 'LB_wifi_ext_mode_80211bg') and (/config_data/main/WifiExt/RR_WifiExt_Mode != 'LB_wifi_ext_mode_80211bgn'))) or (. = 'LB_wifi_ext_band_5GHz' and ((/config_data/main/WifiExt/RR_WifiExt_Mode != 'LB_wifi_ext_mode_80211a') and (/config_data/main/WifiExt/RR_WifiExt_Mode != 'LB_wifi_ext_mode_80211an') and (/config_data/main/WifiExt/RR_WifiExt_Mode != 'LB_wifi_ext_mode_80211anac'))))";
                }
                leaf "RR_WifiExt_Bandwidth" {
                    type "enumeration" {
                        enum "LB_wifi_ext_bandwidth_20MHz" {
                            value "0";
                        }
                        enum "LB_wifi_ext_bandwidth_40MHz" {
                            value "1";
                        }
                        enum "LB_wifi_ext_bandwidth_80MHz" {
                            value "2";
                        }
                    }
                    must "not ((. = 'LB_wifi_ext_bandwidth_40MHz' and ((/config_data/main/WifiExt/RR_WifiExt_Mode != 'LB_wifi_ext_mode_80211a') and (/config_data/main/WifiExt/RR_WifiExt_Mode != 'LB_wifi_ext_mode_80211bgn') and (/config_data/main/WifiExt/RR_WifiExt_Mode != 'LB_wifi_ext_mode_80211an') and (/config_data/main/WifiExt/RR_WifiExt_Mode != 'LB_wifi_ext_mode_80211anac'))) or (. = 'LB_wifi_ext_bandwidth_80MHz' and (/config_data/main/WifiExt/RR_WifiExt_Mode != 'LB_wifi_ext_mode_80211anac')))";
                }
                leaf "RR_WifiExt_Channel24GHz" {
                    when "not (/config_data/main/WifiExt/RR_WifiExt_Band != 'LB_wifi_ext_band_24GHz')";
                    type "enumeration" {
                        enum "LB_wifi_ext_channel_Automatic" {
                            value "0";
                        }
                        enum "LB_wifi_ext_channel_1_2412MHz" {
                            value "1";
                        }
                        enum "LB_wifi_ext_channel_2_2417MHz" {
                            value "2";
                        }
                        enum "LB_wifi_ext_channel_3_2422MHz" {
                            value "3";
                        }
                        enum "LB_wifi_ext_channel_4_2427MHz" {
                            value "4";
                        }
                        enum "LB_wifi_ext_channel_5_2432MHz" {
                            value "5";
                        }
                        enum "LB_wifi_ext_channel_6_2437MHz" {
                            value "6";
                        }
                        enum "LB_wifi_ext_channel_7_2442MHz" {
                            value "7";
                        }
                        enum "LB_wifi_ext_channel_8_2447MHz" {
                            value "8";
                        }
                        enum "LB_wifi_ext_channel_9_2452MHz" {
                            value "9";
                        }
                        enum "LB_wifi_ext_channel_10_2457MHz" {
                            value "10";
                        }
                        enum "LB_wifi_ext_channel_11_2462MHz" {
                            value "11";
                        }
                        enum "LB_wifi_ext_channel_12_2467MHz" {
                            value "12";
                        }
                        enum "LB_wifi_ext_channel_13_2472MHz" {
                            value "13";
                        }
                        enum "LB_wifi_ext_channel_14_2484MHz" {
                            value "14";
                        }
                    }
                    must "not ((. = 'LB_wifi_ext_channel_1_2412MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_2_2417MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_3_2422MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_4_2427MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_5_2432MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_6_2437MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_7_2442MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_8_2447MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_9_2452MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_10_2457MHz' and (/config_data/main/WifiExt/RR_WifiExt_Bandwidth != 'LB_wifi_ext_bandwidth_20MHz')) or (. = 'LB_wifi_ext_channel_11_2462MHz' and (/config_data/main/WifiExt/RR_WifiExt_Bandwidth != 'LB_wifi_ext_bandwidth_20MHz')) or (. = 'LB_wifi_ext_channel_12_2467MHz' and (/config_data/main/WifiExt/RR_WifiExt_Bandwidth != 'LB_wifi_ext_bandwidth_20MHz')) or (. = 'LB_wifi_ext_channel_13_2472MHz' and (/config_data/main/WifiExt/RR_WifiExt_Bandwidth != 'LB_wifi_ext_bandwidth_20MHz')) or (. = 'LB_wifi_ext_channel_14_2484MHz' and (/config_data/main/WifiExt/RR_WifiExt_Bandwidth != 'LB_wifi_ext_bandwidth_20MHz')))";
                }
                leaf "RR_WifiExt_Channel5GHz" {
                    when "not (/config_data/main/WifiExt/RR_WifiExt_Band != 'LB_wifi_ext_band_5GHz')";
                    type "enumeration" {
                        enum "LB_wifi_ext_channel_Automatic" {
                            value "0";
                        }
                        enum "LB_wifi_ext_channel_36_5180MHz" {
                            value "36";
                        }
                        enum "LB_wifi_ext_channel_40_5200MHz" {
                            value "40";
                        }
                        enum "LB_wifi_ext_channel_44_5220MHz" {
                            value "44";
                        }
                        enum "LB_wifi_ext_channel_48_5240MHz" {
                            value "48";
                        }
                        enum "LB_wifi_ext_channel_52_5260MHz" {
                            value "52";
                        }
                        enum "LB_wifi_ext_channel_56_5280MHz" {
                            value "56";
                        }
                        enum "LB_wifi_ext_channel_60_5300MHz" {
                            value "60";
                        }
                        enum "LB_wifi_ext_channel_64_5320MHz" {
                            value "64";
                        }
                        enum "LB_wifi_ext_channel_100_5500MHz" {
                            value "100";
                        }
                        enum "LB_wifi_ext_channel_104_5520MHz" {
                            value "104";
                        }
                        enum "LB_wifi_ext_channel_108_5540MHz" {
                            value "108";
                        }
                        enum "LB_wifi_ext_channel_112_5560MHz" {
                            value "112";
                        }
                        enum "LB_wifi_ext_channel_116_5580MHz" {
                            value "116";
                        }
                        enum "LB_wifi_ext_channel_120_5600MHz" {
                            value "120";
                        }
                        enum "LB_wifi_ext_channel_124_5620MHz" {
                            value "124";
                        }
                        enum "LB_wifi_ext_channel_128_5640MHz" {
                            value "128";
                        }
                        enum "LB_wifi_ext_channel_132_5660MHz" {
                            value "132";
                        }
                        enum "LB_wifi_ext_channel_136_5680MHz" {
                            value "136";
                        }
                        enum "LB_wifi_ext_channel_140_5700MHz" {
                            value "140";
                        }
                        enum "LB_wifi_ext_channel_144_5720MHz" {
                            value "144";
                        }
                        enum "LB_wifi_ext_channel_149_5745MHz" {
                            value "149";
                        }
                        enum "LB_wifi_ext_channel_153_5765MHz" {
                            value "153";
                        }
                        enum "LB_wifi_ext_channel_157_5785MHz" {
                            value "157";
                        }
                        enum "LB_wifi_ext_channel_161_5805MHz" {
                            value "161";
                        }
                        enum "LB_wifi_ext_channel_165_5825MHz" {
                            value "165";
                        }
                    }
                    must "not ((. = 'LB_wifi_ext_channel_40_5200MHz' and (/config_data/main/WifiExt/RR_WifiExt_Bandwidth != 'LB_wifi_ext_bandwidth_20MHz')) or (. = 'LB_wifi_ext_channel_44_5220MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_48_5240MHz' and (/config_data/main/WifiExt/RR_WifiExt_Bandwidth != 'LB_wifi_ext_bandwidth_20MHz')) or (. = 'LB_wifi_ext_channel_56_5280MHz' and (/config_data/main/WifiExt/RR_WifiExt_Bandwidth != 'LB_wifi_ext_bandwidth_20MHz')) or (. = 'LB_wifi_ext_channel_60_5300MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_64_5320MHz' and (/config_data/main/WifiExt/RR_WifiExt_Bandwidth != 'LB_wifi_ext_bandwidth_20MHz')) or (. = 'LB_wifi_ext_channel_104_5520MHz' and (/config_data/main/WifiExt/RR_WifiExt_Bandwidth != 'LB_wifi_ext_bandwidth_20MHz')) or (. = 'LB_wifi_ext_channel_108_5540MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_112_5560MHz' and (/config_data/main/WifiExt/RR_WifiExt_Bandwidth != 'LB_wifi_ext_bandwidth_20MHz')) or (. = 'LB_wifi_ext_channel_120_5600MHz' and (/config_data/main/WifiExt/RR_WifiExt_Bandwidth != 'LB_wifi_ext_bandwidth_20MHz')) or (. = 'LB_wifi_ext_channel_124_5620MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_128_5640MHz' and (/config_data/main/WifiExt/RR_WifiExt_Bandwidth != 'LB_wifi_ext_bandwidth_20MHz')) or (. = 'LB_wifi_ext_channel_136_5680MHz' and (/config_data/main/WifiExt/RR_WifiExt_Bandwidth != 'LB_wifi_ext_bandwidth_20MHz')) or (. = 'LB_wifi_ext_channel_140_5700MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_144_5720MHz' and (/config_data/main/WifiExt/RR_WifiExt_Bandwidth != 'LB_wifi_ext_bandwidth_20MHz')) or (. = 'LB_wifi_ext_channel_153_5765MHz' and (/config_data/main/WifiExt/RR_WifiExt_Bandwidth != 'LB_wifi_ext_bandwidth_20MHz')) or (. = 'LB_wifi_ext_channel_157_5785MHz' and ((/config_data/main/WifiExt/RR_WifiExt_Bandwidth != 'LB_wifi_ext_bandwidth_20MHz') and (/config_data/main/WifiExt/RR_WifiExt_Bandwidth != 'LB_wifi_ext_bandwidth_40MHz'))) or (. = 'LB_wifi_ext_channel_161_5805MHz' and (/config_data/main/WifiExt/RR_WifiExt_Bandwidth != 'LB_wifi_ext_bandwidth_20MHz')) or (. = 'LB_wifi_ext_channel_165_5825MHz' and (/config_data/main/WifiExt/RR_WifiExt_Bandwidth != 'LB_wifi_ext_bandwidth_20MHz')))";
                }
                leaf "RR_WifiExt_AutoTxPower" {
                    when "not (((/config_data/main/WifiExt/RR_WifiExt_Band = 'LB_wifi_ext_band_24GHz') and (/config_data/main/WifiExt/RR_WifiExt_Channel24GHz = 'LB_wifi_ext_channel_Automatic')) or ((/config_data/main/WifiExt/RR_WifiExt_Band = 'LB_wifi_ext_band_5GHz') and (/config_data/main/WifiExt/RR_WifiExt_Channel5GHz = 'LB_wifi_ext_channel_Automatic')))";
                    type "lbox_off_on";
                }
                leaf "RR_WifiExt_TxPower" {
                    when "not ((/config_data/main/WifiExt/RR_WifiExt_AutoTxPower != 'Off') or ((/config_data/main/WifiExt/RR_WifiExt_Band = 'LB_wifi_ext_band_24GHz') and (/config_data/main/WifiExt/RR_WifiExt_Channel24GHz = 'LB_wifi_ext_channel_Automatic')) or ((/config_data/main/WifiExt/RR_WifiExt_Band = 'LB_wifi_ext_band_5GHz') and (/config_data/main/WifiExt/RR_WifiExt_Channel5GHz = 'LB_wifi_ext_channel_Automatic')))";
                    type "uint8" {
                        range "0..16";
                    }
                    must ". <= /config_data/device/DeviceHw/RR_DynHw_Wifi_Ext_TxPowerMax" {
                        error-message "valmsg_it_WifiExt_TxPower";
                    }
                }
                leaf "RR_WifiExt_Antenna1Config" {
                    type "lbox_antenna_config";
                }
                leaf "RR_WifiExt_Antenna2Config" {
                    type "lbox_antenna_config";
                }
                leaf "RR_WifiExt_AntennaGain" {
                    type "uint8" {
                        range "0..30";
                    }
                }
                leaf "RR_WifiExt_CableLoss" {
                    type "uint8" {
                        range "0..30";
                    }
                }
                leaf "RR_WifiExt_Mtu" {
                    when "not (/config_data/main/WifiExt/RR_WifiExt_OperationType != 'LB_wifi_operation_type_Ap')";
                    type "uint16" {
                        range "256..1500";
                    }
                }
            }
            container "Networking" {
                leaf "RR_FirewallL3Mode" {
                    type "lbox_off_on";
                }
                leaf "RR_FirewallL2AccessCtrl" {
                    type "enumeration" {
                        enum "Off" {
                            value "0";
                        }
                        enum "Blacklist" {
                            value "1";
                        }
                        enum "Whitelist" {
                            value "2";
                        }
                    }
                }
                leaf "RR_AdvancedDynRouting" {
                    type "enumeration" {
                        enum "Off" {
                            value "0";
                        }
                        enum "On" {
                            value "1";
                        }
                    }
                    must "not ((. = 'On' and ((/config_data/device/DeviceSwKey/RR_SwKey_Flag_routing_bgp != 'On') and (/config_data/device/DeviceSwKey/RR_SwKey_Flag_routing_ospf != 'On') and (/config_data/device/DeviceSwKey/RR_SwKey_Flag_routing_babel != 'On'))))";
                }
                leaf "RR_NatMode" {
                    type "lbox_off_on";
                }
                leaf "RR_QoSMode" {
                    type "lbox_off_on";
                }
                leaf "RR_LinkManagerEn" {
                    type "enumeration" {
                        enum "Off" {
                            value "0";
                        }
                        enum "On" {
                            value "1";
                        }
                    }
                    must "not ((. = 'On' and (/config_data/device/DeviceSwKey/RR_SwKey_Flag_routing_link_management != 'On')))";
                }
                leaf "RR_FirewallL2Mode" {
                    type "lbox_off_on";
                }
                leaf "RR_PppoeClient_Enable" {
                    type "enumeration" {
                        enum "Off" {
                            value "0";
                        }
                        enum "On" {
                            value "1";
                        }
                    }
                    must "not ((. = 'On' and (/config_data/device/DeviceSwKey/RR_SwKey_Flag_interface_pppoe_client != 'On')))";
                }
                leaf "RR_DhcpServerEn" {
                    type "lbox_off_on";
                }
                leaf "RR_DnsForwardingEn" {
                    type "lbox_off_on";
                }
            }
            container "NetworkingHelpers" {
                leaf "RR_NetHelper_Ftp" {
                    type "lbox_off_on";
                }
                leaf "RR_NetHelper_Ftp_Port" {
                    when "not (/config_data/main/NetworkingHelpers/RR_NetHelper_Ftp != 'On')";
                    type "lim_udp_port";
                }
            }
            container "FirewallL3Log" {
                when "not (/config_data/main/Networking/RR_FirewallL3Mode != 'On')";
                leaf "RR_FirewallL3Log_En" {
                    type "lbox_off_on";
                }
                leaf "RR_FirewallL3Log_PacketCount" {
                    when "not (/config_data/main/FirewallL3Log/RR_FirewallL3Log_En != 'On')";
                    type "lim_fwall_traffic_filter";
                    must ". <= /config_data/main/FirewallL3Log/RR_FirewallL3Log_PacketBurst" {
                        error-message "valmsg_it_FirewallL3Log_PacketCount";
                    }
                }
                leaf "RR_FirewallL3Log_TimePeriod" {
                    when "not (/config_data/main/FirewallL3Log/RR_FirewallL3Log_En != 'On')";
                    type "lbox_fwall_filter_limit_period";
                }
                leaf "RR_FirewallL3Log_PacketBurst" {
                    when "not (/config_data/main/FirewallL3Log/RR_FirewallL3Log_En != 'On')";
                    type "lim_fwall_traffic_filter";
                    must ". >= /config_data/main/FirewallL3Log/RR_FirewallL3Log_PacketCount" {
                        error-message "valmsg_it_FirewallL3Log_PacketBurst";
                    }
                }
            }
            container "FirewallL2AccLog" {
                when "not (/config_data/main/Networking/RR_FirewallL2AccessCtrl = 'Off')";
                leaf "RR_FirewallL2AccLog_En" {
                    type "lbox_off_on";
                }
                leaf "RR_FirewallL2AccLog_FrameCount" {
                    when "not (/config_data/main/FirewallL2AccLog/RR_FirewallL2AccLog_En != 'On')";
                    type "lim_fwall_traffic_filter";
                    must ". <= /config_data/main/FirewallL2AccLog/RR_FirewallL2AccLog_FrameBurst" {
                        error-message "valmsg_it_FirewallL2AccLog_FrameCount";
                    }
                }
                leaf "RR_FirewallL2AccLog_TimePeriod" {
                    when "not (/config_data/main/FirewallL2AccLog/RR_FirewallL2AccLog_En != 'On')";
                    type "lbox_fwall_filter_limit_period";
                }
                leaf "RR_FirewallL2AccLog_FrameBurst" {
                    when "not (/config_data/main/FirewallL2AccLog/RR_FirewallL2AccLog_En != 'On')";
                    type "lim_fwall_traffic_filter";
                    must ". >= /config_data/main/FirewallL2AccLog/RR_FirewallL2AccLog_FrameCount" {
                        error-message "valmsg_it_FirewallL2AccLog_FrameBurst";
                    }
                }
            }
            container "FirewallL2FwdLog" {
                when "not (/config_data/main/Networking/RR_FirewallL2Mode != 'On')";
                leaf "RR_FirewallL2FwdLog_En" {
                    type "lbox_off_on";
                }
                leaf "RR_FirewallL2FwdLog_FrameCount" {
                    when "not (/config_data/main/FirewallL2FwdLog/RR_FirewallL2FwdLog_En != 'On')";
                    type "lim_fwall_traffic_filter";
                    must ". <= /config_data/main/FirewallL2FwdLog/RR_FirewallL2FwdLog_FrameBurst" {
                        error-message "valmsg_it_FirewallL2FwdLog_FrameCount";
                    }
                }
                leaf "RR_FirewallL2FwdLog_TimePeriod" {
                    when "not (/config_data/main/FirewallL2FwdLog/RR_FirewallL2FwdLog_En != 'On')";
                    type "lbox_fwall_filter_limit_period";
                }
                leaf "RR_FirewallL2FwdLog_FrameBurst" {
                    when "not (/config_data/main/FirewallL2FwdLog/RR_FirewallL2FwdLog_En != 'On')";
                    type "lim_fwall_traffic_filter";
                    must ". >= /config_data/main/FirewallL2FwdLog/RR_FirewallL2FwdLog_FrameCount" {
                        error-message "valmsg_it_FirewallL2FwdLog_FrameBurst";
                    }
                }
            }
            container "NatLog" {
                when "not (/config_data/main/Networking/RR_NatMode != 'On')";
                leaf "RR_NatLog_En" {
                    type "lbox_off_on";
                }
                leaf "RR_NatLog_PacketCount" {
                    when "not (/config_data/main/NatLog/RR_NatLog_En != 'On')";
                    type "lim_fwall_traffic_filter";
                    must ". <= /config_data/main/NatLog/RR_NatLog_PacketBurst" {
                        error-message "valmsg_it_NatLog_PacketCount";
                    }
                }
                leaf "RR_NatLog_TimePeriod" {
                    when "not (/config_data/main/NatLog/RR_NatLog_En != 'On')";
                    type "lbox_fwall_filter_limit_period";
                }
                leaf "RR_NatLog_PacketBurst" {
                    when "not (/config_data/main/NatLog/RR_NatLog_En != 'On')";
                    type "lim_fwall_traffic_filter";
                    must ". >= /config_data/main/NatLog/RR_NatLog_PacketCount" {
                        error-message "valmsg_it_NatLog_PacketBurst";
                    }
                }
            }
            container "DnsForwarding" {
                when "not (/config_data/main/Networking/RR_DnsForwardingEn != 'On')";
                leaf "RR_DnsFwd_SrvPort" {
                    type "lim_udp_port";
                }
                leaf "RR_DnsFwd_ServerList" {
                    type "enumeration" {
                        enum "LB_DnsFwd_ServerList_V_Static" {
                            value "0";
                        }
                        enum "LB_DnsFwd_ServerList_V_Dynamic" {
                            value "1";
                        }
                    }
                }
                leaf "RR_DnsFwd_SrvSelection" {
                    type "enumeration" {
                        enum "LB_DnsFwd_SrvSelection_V_Round_robin" {
                            value "0";
                        }
                        enum "LB_DnsFwd_SrvSelection_V_Strict_order" {
                            value "1";
                        }
                        enum "LB_DnsFwd_SrvSelection_V_All_simult" {
                            value "2";
                        }
                    }
                }
                leaf "RR_DnsFwd_DynSrvSource" {
                    when "not (/config_data/main/DnsForwarding/RR_DnsFwd_ServerList != 'LB_DnsFwd_ServerList_V_Dynamic')";
                    type "enumeration" {
                        enum "WWAN (MAIN)" {
                            value "0";
                        }
                        enum "WWAN (EXT)" {
                            value "1";
                        }
                        enum "PPP 1" {
                            value "2";
                        }
                        enum "PPP 2" {
                            value "3";
                        }
                        enum "PPP 3" {
                            value "4";
                        }
                        enum "LB_Routing_Mode_Pppoe_client" {
                            value "5";
                        }
                    }
                    must "not ((. = 'WWAN (MAIN)' and (/config_data/device/DeviceHw/RR_DynHw_Primary_Cellular != 'On')) or (. = 'WWAN (EXT)' and (/config_data/device/DeviceHw/RR_DynHw_Module_Cellular != 'On')) or (. = 'PPP 1' and (/config_data/device/DeviceHw/RR_DynHw_Port_Com1 != 'On')) or (. = 'PPP 2' and (/config_data/device/DeviceHw/RR_DynHw_Port_Com2 != 'On')) or (. = 'PPP 3' and (/config_data/device/DeviceHw/RR_DynHw_Port_Com3 != 'On')))";
                }
                leaf "RR_DnsFwd_Cache" {
                    type "lbox_off_on";
                }
                leaf "RR_DnsFwd_MaxRequests" {
                    type "uint8" {
                        range "5..250";
                    }
                }
                leaf "RR_DnsFwd_CacheSize" {
                    when "not (/config_data/main/DnsForwarding/RR_DnsFwd_Cache != 'On')";
                    type "uint16" {
                        range "50..10000";
                    }
                }
                leaf "RR_DnsFwd_ServeLocal" {
                    type "lbox_off_on";
                }
                leaf "RR_DnsFwd_IsolateLocalNet" {
                    type "lbox_off_on";
                }
                leaf "RR_DnsFwd_DetectLoops" {
                    type "lbox_off_on";
                }
                leaf "RR_DnsFwd_FilterWindows" {
                    type "lbox_off_on";
                }
                leaf "RR_DnsFwd_DnsSec" {
                    when "not (/config_data/main/DnsForwarding/RR_DnsFwd_Cache != 'On')";
                    type "lbox_off_on";
                }
            }
            container "AdvDynamicRouting" {
                when "not (/config_data/main/Networking/RR_AdvancedDynRouting != 'On')";
                leaf "RR_ADR_RouterId" {
                    type "inet:ipv4-address";
                }
                leaf "RR_ADR_OspfEn" {
                    type "enumeration" {
                        enum "Off" {
                            value "0";
                        }
                        enum "On" {
                            value "1";
                        }
                    }
                    must "not ((. = 'On' and (/config_data/device/DeviceSwKey/RR_SwKey_Flag_routing_ospf != 'On')))";
                }
                leaf "RR_ADR_BgpEn" {
                    type "enumeration" {
                        enum "Off" {
                            value "0";
                        }
                        enum "On" {
                            value "1";
                        }
                    }
                    must "not ((. = 'On' and (/config_data/device/DeviceSwKey/RR_SwKey_Flag_routing_bgp != 'On')))";
                }
                leaf "RR_ADR_BabelEn" {
                    type "enumeration" {
                        enum "Off" {
                            value "0";
                        }
                        enum "On" {
                            value "1";
                        }
                    }
                    must "not ((. = 'On' and (/config_data/device/DeviceSwKey/RR_SwKey_Flag_routing_babel != 'On')))";
                }
                leaf "RR_ADR_KernelMetric" {
                    type "lim_routing_metric_dyn";
                }
            }
            container "Ospf" {
                when "not ((/config_data/main/Networking/RR_AdvancedDynRouting != 'On') or (/config_data/main/AdvDynamicRouting/RR_ADR_OspfEn != 'On'))";
                leaf "RR_Ospf_InstanceId" {
                    type "lim_uint_8";
                }
                leaf "RR_OspfImFil_Policy" {
                    type "lbox_adr_filter_policy";
                }
                leaf "RR_OspfExFil_Policy" {
                    type "lbox_adr_filter_policy";
                }
            }
            container "Bgp" {
                when "not ((/config_data/main/Networking/RR_AdvancedDynRouting != 'On') or (/config_data/main/AdvDynamicRouting/RR_ADR_BgpEn != 'On'))";
                leaf "RR_Bgp_LocalAS" {
                    type "lim_uint_32";
                }
                leaf "RR_Bgp_LocalRouterPreference" {
                    type "lim_uint_32";
                }
                leaf "RR_Bgp_SetMED" {
                    type "enumeration" {
                        enum "Off" {
                            value "0";
                        }
                        enum "Static" {
                            value "1";
                        }
                        enum "OSPF metric 1" {
                            value "2";
                        }
                        enum "Babel metric" {
                            value "3";
                        }
                    }
                    must "not ((. = 'OSPF metric 1' and (/config_data/main/AdvDynamicRouting/RR_ADR_OspfEn != 'On')) or (. = 'Babel metric' and (/config_data/main/AdvDynamicRouting/RR_ADR_BabelEn != 'On')))";
                }
                leaf "RR_Bgp_RouteReflector" {
                    type "lbox_off_on";
                }
                leaf "RR_Bgp_RRClusterIdType" {
                    when "not (/config_data/main/Bgp/RR_Bgp_RouteReflector != 'On')";
                    type "enumeration" {
                        enum "Router Id" {
                            value "0";
                        }
                        enum "Manual" {
                            value "1";
                        }
                    }
                }
                leaf "RR_BgpImIgpFil_Policy" {
                    type "lbox_adr_filter_policy";
                }
                leaf "RR_BgpExIgpFil_Policy" {
                    type "lbox_adr_filter_policy";
                }
                leaf "RR_BgpImOutFil_Policy" {
                    type "lbox_adr_filter_policy";
                }
                leaf "RR_BgpExOutFil_Policy" {
                    type "lbox_adr_filter_policy";
                }
                leaf "RR_Bgp_StaticMED" {
                    when "not (/config_data/main/Bgp/RR_Bgp_SetMED = 'Off')";
                    type "lim_uint_32";
                }
                leaf "RR_Bgp_RRClusterId" {
                    when "not ((/config_data/main/Bgp/RR_Bgp_RouteReflector != 'On') or (/config_data/main/Bgp/RR_Bgp_RRClusterIdType != 'Manual'))";
                    type "inet:ipv4-address";
                }
                leaf "RR_BgpImOutFil_Limit" {
                    type "lim_uint_16_1toFF";
                }
            }
            container "Babel" {
                when "not ((/config_data/main/Networking/RR_AdvancedDynRouting != 'On') or (/config_data/main/AdvDynamicRouting/RR_ADR_BabelEn != 'On'))";
                leaf "RR_Babel_RandomizeId" {
                    type "lbox_off_on";
                }
                leaf "RR_BabelRelFil_Policy" {
                    type "lbox_adr_filter_policy";
                }
                leaf "RR_BabelImFil_Policy" {
                    type "lbox_adr_filter_policy";
                }
                leaf "RR_BabelExFil_Policy" {
                    type "lbox_adr_filter_policy";
                }
                leaf "RR_BabelPreFil_Poisoned" {
                    type "lbox_off_on";
                }
                leaf "RR_BabelPreFil_LimitMetric" {
                    type "lbox_off_on";
                }
                leaf "RR_BabelPreFil_LimitMetricThr" {
                    when "not (/config_data/main/Babel/RR_BabelPreFil_LimitMetric != 'On')";
                    type "lim_adr_babel_metric";
                }
            }
            container "LinkManager" {
                when "not (/config_data/main/Networking/RR_LinkManagerEn != 'On')";
                description "Cnf. group for Link Manager: common";
                leaf "RR_LinkMng_IpSecControl" {
                    when "not (/config_data/main/VPN/RR_IpSecEnable != 'On')";
                    type "lbox_off_on";
                }
            }
            container "PppoeClient" {
                when "not (/config_data/main/Networking/RR_PppoeClient_Enable != 'On')";
                leaf "RR_PppoeClient_MngEn" {
                    type "lbox_off_on";
                }
                leaf "RR_PppoeClient_Masquerade" {
                    type "lbox_off_on";
                }
                leaf "RR_PppoeClient_NetMask" {
                    type "lim_ipv4_mask0";
                }
                leaf "RR_PppoeClient_CtrlMsgLogEn" {
                    type "lbox_off_on";
                }
                leaf "RR_PppoeClient_IfaceIdSelect" {
                    type "enumeration" {
                        enum "LB_lan_vlan_iface_select_Lan" {
                            value "0";
                        }
                        enum "LB_lan_vlan_iface_select_Vlan" {
                            value "1";
                        }
                    }
                }
                leaf "RR_PppoeClient_RmtAccEn" {
                    when "not (/config_data/main/UserAccess/RR_UsAcc_RmtAccess_Enable != 'On')";
                    type "lbox_off_on";
                }
                leaf "RR_PppoeClient_IfaceIdVlan" {
                    when "not (/config_data/main/PppoeClient/RR_PppoeClient_IfaceIdSelect != 'LB_lan_vlan_iface_select_Vlan')";
                    type "lim_uint_16";
                }
                leaf "RR_PppoeClient_IfaceIdLan" {
                    when "not (/config_data/main/PppoeClient/RR_PppoeClient_IfaceIdSelect != 'LB_lan_vlan_iface_select_Lan')";
                    type "lim_uint_16";
                }
                leaf "RR_PppoeClient_Username" {
                    type "string" {
                        pattern "[ !#%-:<-\\[\\]-_a-~]{0,64}";
                    }
                }
                leaf "RR_PppoeClient_Password" {
                    type "string" {
                        pattern "[ !#%-:<-\\[\\]-_a-~]{0,64}";
                    }
                }
                leaf "RR_PppoeClient_SvcName" {
                    type "string" {
                        pattern "[^\"`\\\\$;]{0,64}";
                    }
                }
                leaf "RR_PppoeClient_AcName" {
                    type "string" {
                        pattern "[^\"`\\\\$;]{0,64}";
                    }
                }
                leaf "RR_PppoeClient_HostUniq" {
                    type "string" {
                        pattern "([0-9a-fA-F][0-9a-fA-F])*";
                    }
                    must "string-length(.) <= 64" {
                        error-message "valmsg_it_Pppoe_Client_HostUniq";
                    }
                }
                leaf "RR_PppoeClient_LcpKeepFailureCnt" {
                    type "lim_uint_8";
                }
                leaf "RR_PppoeClient_LcpKeepInterval" {
                    when "not (/config_data/main/PppoeClient/RR_PppoeClient_LcpKeepFailureCnt = '0')";
                    type "lim_uint_16_1toFF";
                }
                leaf "RR_PppoeClient_IdleTimeout" {
                    type "lim_uint_16";
                }
            }
            container "VPN" {
                leaf "RR_IpSecEnable" {
                    type "enumeration" {
                        enum "Off" {
                            value "0";
                        }
                        enum "On" {
                            value "1";
                        }
                    }
                    must "not ((. = 'On' and ((/config_data/device/DeviceHw/RR_DynHw_NoCrypt = 'On') or (/config_data/device/DeviceSwKey/RR_SwKey_Flag_vpn_ipsec != 'On'))))";
                }
                leaf "RR_GreL2Enable" {
                    type "enumeration" {
                        enum "Off" {
                            value "0";
                        }
                        enum "On" {
                            value "1";
                        }
                    }
                    must "not ((. = 'On' and (/config_data/device/DeviceSwKey/RR_SwKey_Flag_vpn_gre != 'On')))";
                }
                leaf "RR_GreL3Enable" {
                    type "enumeration" {
                        enum "Off" {
                            value "0";
                        }
                        enum "On" {
                            value "1";
                        }
                    }
                    must "not ((. = 'On' and (/config_data/device/DeviceSwKey/RR_SwKey_Flag_vpn_gre != 'On')))";
                }
                leaf "RR_OpenVpnEnable" {
                    type "enumeration" {
                        enum "Off" {
                            value "0";
                        }
                        enum "On" {
                            value "1";
                        }
                    }
                    must "not ((. = 'On' and ((/config_data/device/DeviceHw/RR_DynHw_NoCrypt = 'On') or (/config_data/device/DeviceSwKey/RR_SwKey_Flag_vpn_openvpn != 'On'))))";
                }
            }
            container "IpSecGlobal" {
                when "not (/config_data/main/VPN/RR_IpSecEnable != 'On')";
                leaf "RR_IpSecMakeBeforeBreak" {
                    type "lbox_off_on";
                }
            }
            container "Vrrp" {
                leaf "RR_Vrrp_Enable" {
                    type "enumeration" {
                        enum "Off" {
                            value "0";
                        }
                        enum "On" {
                            value "1";
                        }
                    }
                    must "not ((. = 'On' and (/config_data/auth/CnfAuth/RR_CnfAuthCnfVersion >= 0)))";
                }
                leaf "RR_Vrrp_VRID" {
                    when "not (/config_data/main/Vrrp/RR_Vrrp_Enable != 'On')";
                    type "uint8" {
                        range "1..255";
                    }
                }
                leaf "RR_Vrrp_Prio" {
                    when "not (/config_data/main/Vrrp/RR_Vrrp_Enable != 'On')";
                    type "uint8" {
                        range "0..255";
                    }
                }
                leaf "RR_Vrrp_Timeout" {
                    when "not (/config_data/main/Vrrp/RR_Vrrp_Enable != 'On')";
                    type "uint8" {
                        range "0..255";
                    }
                }
            }
            container "HotStdby" {
                when "not (/config_data/device/DeviceHw/RR_DynHw_HotStandby != 'On')";
                leaf "RR_HotStdby_Enable" {
                    type "lbox_off_on";
                }
                leaf "RR_HotStdby_ToggleEnable" {
                    when "not (/config_data/main/HotStdby/RR_HotStdby_Enable != 'On')";
                    type "enumeration" {
                        enum "Off" {
                            value "0";
                        }
                        enum "On" {
                            value "1";
                        }
                    }
                    must "not ((. = 'On' and (/config_data/auth/CnfAuth/RR_CnfAuthCnfVersion >= 0)))";
                }
                leaf "RR_HotStdby_MasterMode" {
                    when "not (/config_data/main/HotStdby/RR_HotStdby_Enable != 'On')";
                    type "enumeration" {
                        enum "HS_master" {
                            value "0";
                        }
                        enum "HS_slave" {
                            value "1";
                        }
                    }
                }
                leaf "RR_HotStdby_FallbackTime" {
                    when "not ((/config_data/main/HotStdby/RR_HotStdby_Enable != 'On') or (/config_data/main/HotStdby/RR_HotStdby_MasterMode = 'HS_slave'))";
                    type "uint16" {
                        range "15..8191";
                    }
                }
                leaf "RR_HotStdby_Mac" {
                    when "not (/config_data/main/HotStdby/RR_HotStdby_Enable != 'On')";
                    type "yang:mac-address";
                }
                leaf "RR_HotStdby_Ip" {
                    when "not (/config_data/main/HotStdby/RR_HotStdby_Enable != 'On')";
                    type "inet:ipv4-address";
                }
                leaf "RR_HotStdby_ToggleSwitchPeriod" {
                    when "not ((/config_data/main/HotStdby/RR_HotStdby_Enable != 'On') or (/config_data/main/HotStdby/RR_HotStdby_ToggleEnable != 'On'))";
                    type "uint32" {
                        range "60..8640000";
                    }
                }
                leaf "RR_HotStdby_ToggleSwitchTime" {
                    when "not ((/config_data/main/HotStdby/RR_HotStdby_Enable != 'On') or (/config_data/main/HotStdby/RR_HotStdby_ToggleEnable != 'On'))";
                    type "uint32" {
                        range "5..4320000";
                    }
                }
                leaf "RR_HotStdby_RadioMac" {
                    when "not ((/config_data/device/DeviceHw/RR_DynHw_Primary_Radio != 'On') or (/config_data/main/HotStdby/RR_HotStdby_Enable != 'On'))";
                    type "yang:mac-address";
                }
                leaf "RR_HotStdby_MngEn" {
                    when "not (/config_data/main/HotStdby/RR_HotStdby_Enable != 'On')";
                    type "lbox_off_on";
                }
                leaf "RR_HotStdby_RmtAccEn" {
                    when "not ((/config_data/main/HotStdby/RR_HotStdby_Enable != 'On') or (/config_data/main/UserAccess/RR_UsAcc_RmtAccess_Enable != 'On'))";
                    type "lbox_off_on";
                }
            }
            container "HotStdbyGuardEth" {
                when "not ((/config_data/device/DeviceHw/RR_DynHw_HotStandby != 'On') or (/config_data/main/HotStdby/RR_HotStdby_Enable != 'On'))";
                leaf "RR_HotStdby_Guard_Mode" {
                    type "enumeration" {
                        enum "INCLUDE" {
                            value "0";
                        }
                        enum "EXCLUDE" {
                            value "1";
                        }
                    }
                }
            }
            container "SleepMode" {
                leaf "RR_Sleep_Enable" {
                    type "enumeration" {
                        enum "Off" {
                            value "0";
                        }
                        enum "On" {
                            value "1";
                        }
                    }
                    must "not ((. = 'On' and (((/config_data/device/DeviceHw/RR_DynHw_HotStandby = 'On') and (/config_data/main/HotStdby/RR_HotStdby_Enable = 'On')) or ((/config_data/device/DeviceHw/RR_DynHw_Primary_Radio = 'On') and (/config_data/main/RadioProtocol/RR_RadioAccessProtocol = 'Base driven') and (/config_data/main/RadioProtocolBaseDr/RR_RadioBDP_StationType = 'Base')))))";
                }
                leaf "RR_Sleep_WakeOnTime" {
                    when "not ((/config_data/device/DeviceHw/RR_DynHw_Rtc != 'On') or (/config_data/main/SleepMode/RR_Sleep_Enable != 'On'))";
                    type "lbox_off_on";
                }
                leaf "RR_Sleep_SleepOnTime" {
                    when "not (/config_data/main/SleepMode/RR_Sleep_Enable != 'On')";
                    type "lbox_off_on";
                }
                leaf "RR_Sleep_WakeOnSI" {
                    when "not (/config_data/main/SleepMode/RR_Sleep_Enable != 'On')";
                    type "lbox_off_on";
                }
            }
            container "SleepModeWakeTime" {
                when "not ((/config_data/device/DeviceHw/RR_DynHw_Rtc != 'On') or (/config_data/main/SleepMode/RR_Sleep_Enable != 'On') or (/config_data/main/SleepMode/RR_Sleep_WakeOnTime != 'On'))";
                leaf "RR_SleepWT_WakeFrom_H" {
                    type "lim_time_hours_day";
                }
                leaf "RR_SleepWT_WakeFrom_M" {
                    type "lim_time_minutes_hr";
                }
                leaf "RR_SleepWT_WakeUntil_M" {
                    type "lim_time_minutes_hr";
                }
                leaf "RR_SleepWT_WakeUntil_H" {
                    type "lim_time_hours_day";
                }
                leaf "RR_SleepWT_Period" {
                    type "uint16" {
                        range "5..1439";
                    }
                }
            }
            container "SleepModeSleepTime" {
                when "not ((/config_data/main/SleepMode/RR_Sleep_Enable != 'On') or (/config_data/main/SleepMode/RR_Sleep_SleepOnTime != 'On'))";
                leaf "RR_SleepST_PowerOnInterval" {
                    type "uint16" {
                        range "5..1439";
                    }
                }
                leaf "RR_SleepST_WakingReset" {
                    type "lbox_off_on";
                }
                leaf "RR_SleepST_WReset_OnMainAct" {
                    when "not ((/config_data/main/SleepModeSleepTime/RR_SleepST_WakingReset != 'On') or ((/config_data/device/DeviceHw/RR_DynHw_Primary_Radio != 'On') and ((/config_data/device/DeviceHw/RR_DynHw_Primary_Cellular != 'On') or (/config_data/main/Cellular/RR_CellMain_Enable != 'On'))))";
                    type "lbox_off_on";
                }
                leaf "RR_SleepST_WReset_OnExtAct" {
                    when "not ((/config_data/main/SleepModeSleepTime/RR_SleepST_WakingReset != 'On') or (((/config_data/device/DeviceHw/RR_DynHw_Module_Cellular != 'On') or (/config_data/main/Cellular/RR_CellAux_Enable != 'On')) and ((/config_data/device/DeviceHw/RR_DynHw_Module_Wifi != 'On') or (/config_data/main/Wifi/RR_WifiExt_Enable != 'On'))))";
                    type "lbox_off_on";
                }
            }
            container "STP" {
                leaf "RR_STP_Priority" {
                    when "not (/config_data/main/STP/RR_STP_Ena != 'On')";
                    type "uint16" {
                        range "0..32768";
                    }
                }
                leaf "RR_STP_FwdDelay" {
                    when "not (/config_data/main/STP/RR_STP_Ena != 'On')";
                    type "uint8" {
                        range "2..30";
                    }
                }
                leaf "RR_STP_Ena" {
                    type "lbox_off_on";
                }
                leaf "RR_STP_HelloTime" {
                    when "not (/config_data/main/STP/RR_STP_Ena != 'On')";
                    type "uint8" {
                        range "1..10";
                    }
                }
                leaf "RR_STP_MaxAge" {
                    when "not (/config_data/main/STP/RR_STP_Ena != 'On')";
                    type "uint8" {
                        range "6..40";
                    }
                }
            }
            container "UserAccess" {
                leaf "RR_UsAcc_RadiusAuth" {
                    type "enumeration" {
                        enum "Off" {
                            value "0";
                        }
                        enum "On" {
                            value "1";
                        }
                    }
                    must "not ((. = 'On' and (/config_data/device/DeviceSwKey/RR_SwKey_Flag_adm_radius != 'On')))";
                }
                leaf "RR_UsAcc_Ssh_Enable" {
                    type "lbox_off_on";
                }
                leaf "RR_UsAcc_Http_Enable" {
                    type "lbox_off_on";
                }
                leaf "RR_UsAcc_WebSrvCertSource" {
                    type "lbox_default_user";
                }
                leaf "RR_UsAcc_WebInactTimeout" {
                    type "uint16" {
                        range "5..2880";
                    }
                }
                leaf "RR_UsAcc_RmtAccessClientKeySource" {
                    when "not (/config_data/main/UserAccess/RR_UsAcc_RmtAccess_Enable != 'On')";
                    type "lbox_default_user";
                }
                leaf "RR_UsAcc_RmtAccess_Enable" {
                    type "lbox_off_on";
                }
                leaf "RR_UsAcc_Netconf_Enable" {
                    type "lbox_off_on";
                }
                leaf "RR_UsAcc_NetconfCli_Enable" {
                    type "lbox_off_on";
                }
                leaf "RR_UsAcc_Passwd_MinLen" {
                    type "uint8" {
                        range "5..64";
                    }
                }
                leaf "RR_UsAcc_Passwd_MinLCase" {
                    type "uint8" {
                        range "0..5";
                    }
                }
                leaf "RR_UsAcc_Passwd_MinUCase" {
                    type "uint8" {
                        range "0..5";
                    }
                }
                leaf "RR_UsAcc_Passwd_MinDigit" {
                    type "uint8" {
                        range "0..5";
                    }
                }
                leaf "RR_UsAcc_Passwd_MinSpec" {
                    type "uint8" {
                        range "0..5";
                    }
                }
                leaf "RR_UsAcc_Ssh_Port" {
                    when "not (/config_data/main/UserAccess/RR_UsAcc_Ssh_Enable != 'On')";
                    type "lim_udp_port";
                }
                leaf "RR_UsAcc_Http_Port" {
                    when "not (/config_data/main/UserAccess/RR_UsAcc_Http_Enable != 'On')";
                    type "lim_udp_port";
                }
                leaf "RR_UsAcc_Https_Port" {
                    type "lim_udp_port";
                }
                leaf "RR_UsAcc_Netconf_Port" {
                    when "not (/config_data/main/UserAccess/RR_UsAcc_Netconf_Enable != 'On')";
                    type "uint16";
                }
                leaf "RR_UsAcc_NetconfCli_Port" {
                    when "not (/config_data/main/UserAccess/RR_UsAcc_NetconfCli_Enable != 'On')";
                    type "lim_unpriv_port";
                }
            }
            container "UsAccRadius" {
                when "not (/config_data/main/UserAccess/RR_UsAcc_RadiusAuth != 'On')";
                leaf "RR_UsAccRad_ServerAddr" {
                    type "inet:ipv4-address";
                }
                leaf "RR_UsAccRad_Realm" {
                    type "string" {
                        pattern "(.{0}|[^\"`\\\\$;.]+\\.[^\"`\\\\$;]+)";
                    }
                    must "string-length(.) <= 32" {
                        error-message "valmsg_it_UsAccRad_Realm";
                    }
                }
                leaf "RR_UsAccRad_ReqTimeout" {
                    type "uint8" {
                        range "1..30";
                    }
                }
                leaf "RR_UsAccRad_ReqRetries" {
                    type "uint8" {
                        range "1..7";
                    }
                }
                leaf "RR_UsAccRad_AccLvlSource" {
                    type "enumeration" {
                        enum "Static" {
                            value "0";
                        }
                        enum "From server" {
                            value "1";
                        }
                    }
                }
                leaf "RR_UsAccRad_AccLvlStatic" {
                    when "not (/config_data/main/UsAccRadius/RR_UsAccRad_AccLvlSource != 'Static')";
                    type "enumeration" {
                        enum "guest" {
                            value "0";
                        }
                        enum "tech" {
                            value "1";
                        }
                        enum "sectech" {
                            value "2";
                        }
                        enum "admin" {
                            value "3";
                        }
                    }
                }
                leaf "RR_UsAccRad_MapGuest_From" {
                    when "not (/config_data/main/UsAccRadius/RR_UsAccRad_AccLvlSource != 'From server')";
                    type "lim_uint_32";
                    must ". <= /config_data/main/UsAccRadius/RR_UsAccRad_MapGuest_To" {
                        error-message "valmsg_it_UsAccRad_MapGuest_From";
                    }
                }
                leaf "RR_UsAccRad_MapGuest_To" {
                    when "not (/config_data/main/UsAccRadius/RR_UsAccRad_AccLvlSource != 'From server')";
                    type "lim_uint_32";
                    must ". >= /config_data/main/UsAccRadius/RR_UsAccRad_MapGuest_From" {
                        error-message "valmsg_it_UsAccRad_MapGuest_To";
                    }
                    must ". <= /config_data/main/UsAccRadius/RR_UsAccRad_MapTech_From - 1" {
                        error-message "valmsg_it_UsAccRad_MapGuest_To";
                    }
                }
                leaf "RR_UsAccRad_MapTech_From" {
                    when "not (/config_data/main/UsAccRadius/RR_UsAccRad_AccLvlSource != 'From server')";
                    type "lim_uint_32";
                    must ". >= /config_data/main/UsAccRadius/RR_UsAccRad_MapGuest_To + 1" {
                        error-message "valmsg_it_UsAccRad_MapTech_From";
                    }
                    must ". <= /config_data/main/UsAccRadius/RR_UsAccRad_MapTech_To" {
                        error-message "valmsg_it_UsAccRad_MapTech_From";
                    }
                }
                leaf "RR_UsAccRad_MapTech_To" {
                    when "not (/config_data/main/UsAccRadius/RR_UsAccRad_AccLvlSource != 'From server')";
                    type "lim_uint_32";
                    must ". >= /config_data/main/UsAccRadius/RR_UsAccRad_MapTech_From" {
                        error-message "valmsg_it_UsAccRad_MapTech_To";
                    }
                    must ". <= /config_data/main/UsAccRadius/RR_UsAccRad_MapSecTech_From - 1" {
                        error-message "valmsg_it_UsAccRad_MapTech_To";
                    }
                }
                leaf "RR_UsAccRad_MapSecTech_From" {
                    when "not (/config_data/main/UsAccRadius/RR_UsAccRad_AccLvlSource != 'From server')";
                    type "lim_uint_32";
                    must ". >= /config_data/main/UsAccRadius/RR_UsAccRad_MapTech_To + 1" {
                        error-message "valmsg_it_UsAccRad_MapSecTech_From";
                    }
                    must ". <= /config_data/main/UsAccRadius/RR_UsAccRad_MapSecTech_To" {
                        error-message "valmsg_it_UsAccRad_MapSecTech_From";
                    }
                }
                leaf "RR_UsAccRad_MapSecTech_To" {
                    when "not (/config_data/main/UsAccRadius/RR_UsAccRad_AccLvlSource != 'From server')";
                    type "lim_uint_32";
                    must ". >= /config_data/main/UsAccRadius/RR_UsAccRad_MapSecTech_From" {
                        error-message "valmsg_it_UsAccRad_MapSecTech_To";
                    }
                    must ". <= /config_data/main/UsAccRadius/RR_UsAccRad_MapAdmin_From - 1" {
                        error-message "valmsg_it_UsAccRad_MapSecTech_To";
                    }
                }
                leaf "RR_UsAccRad_MapAdmin_From" {
                    when "not (/config_data/main/UsAccRadius/RR_UsAccRad_AccLvlSource != 'From server')";
                    type "lim_uint_32";
                    must ". >= /config_data/main/UsAccRadius/RR_UsAccRad_MapSecTech_To + 1" {
                        error-message "valmsg_it_UsAccRad_MapAdmin_From";
                    }
                    must ". <= /config_data/main/UsAccRadius/RR_UsAccRad_MapAdmin_To" {
                        error-message "valmsg_it_UsAccRad_MapAdmin_From";
                    }
                }
                leaf "RR_UsAccRad_MapAdmin_To" {
                    when "not (/config_data/main/UsAccRadius/RR_UsAccRad_AccLvlSource != 'From server')";
                    type "lim_uint_32";
                    must ". >= /config_data/main/UsAccRadius/RR_UsAccRad_MapAdmin_From" {
                        error-message "valmsg_it_UsAccRad_MapAdmin_To";
                    }
                }
                leaf "RR_UsAccRad_Key" {
                    type "string" {
                        pattern "[^\"`\\\\$;]{0,32}";
                    }
                }
            }
            container "UsAccWebSrvCert" {
                when "not (/config_data/main/UserAccess/RR_UsAcc_WebSrvCertSource != 'LB_default_user_User')";
                leaf "RR_UsAccWSC_PrivKeyId" {
                    type "string" {
                        pattern "[a-zA-Z0-9_]{0,128}";
                    }
                }
                leaf "RR_UsAccWSC_CertId" {
                    type "string" {
                        pattern "[a-zA-Z0-9_]{0,128}";
                    }
                }
                leaf "RR_UsAccWSC_CAChainId" {
                    type "string" {
                        pattern "[a-zA-Z0-9_]{0,128}";
                    }
                }
                leaf "RR_UsAccWSC_DHParamsId" {
                    type "string" {
                        pattern "[a-zA-Z0-9_]{0,128}";
                    }
                }
            }
            container "UsAccRmtAccClientKey" {
                when "not ((/config_data/main/UserAccess/RR_UsAcc_RmtAccess_Enable != 'On') or (/config_data/main/UserAccess/RR_UsAcc_RmtAccessClientKeySource != 'LB_default_user_User'))";
                leaf "RR_UsAccRmtA_ClientPrivKeyId" {
                    type "string" {
                        pattern "[a-zA-Z0-9_]{0,128}";
                    }
                }
            }
            container "SNMP" {
                leaf "RR_SnmpMode" {
                    type "enumeration" {
                        enum "Off" {
                            value "0";
                        }
                        enum "v1_v2c_v3" {
                            value "1";
                        }
                        enum "v3" {
                            value "2";
                        }
                    }
                }
                leaf "RR_SnmpV3_SecLevel" {
                    when "not (/config_data/main/SNMP/RR_SnmpMode = 'Off')";
                    type "enumeration" {
                        enum "NoAuthNoPriv" {
                            value "0";
                        }
                        enum "AuthNoPriv" {
                            value "1";
                        }
                        enum "AuthPriv" {
                            value "2";
                        }
                    }
                }
                leaf "RR_SnmpNotification" {
                    when "not (/config_data/main/SNMP/RR_SnmpMode = 'Off')";
                    type "enumeration" {
                        enum "Off" {
                            value "0";
                        }
                        enum "Trap" {
                            value "1";
                        }
                        enum "Inform" {
                            value "2";
                        }
                    }
                }
                leaf "RR_SnmpNotifVersion" {
                    when "not ((/config_data/main/SNMP/RR_SnmpMode = 'Off') or (/config_data/main/SNMP/RR_SnmpNotification = 'Off'))";
                    type "enumeration" {
                        enum "v1" {
                            value "0";
                        }
                        enum "v2c" {
                            value "1";
                        }
                        enum "v3" {
                            value "2";
                        }
                    }
                    must "not ((. = 'v1' and (/config_data/main/SNMP/RR_SnmpNotification = 'Inform')) or (. = 'v3' and (/config_data/main/SNMP/RR_SnmpNotification = 'Inform')))";
                }
                leaf "RR_SnmpInformTimeout" {
                    when "not ((/config_data/main/SNMP/RR_SnmpMode = 'Off') or (/config_data/main/SNMP/RR_SnmpNotification != 'Inform'))";
                    type "decimal64" {
                        fraction-digits "1";
                        range "0.1..20.0";
                    }
                }
                leaf "RR_SnmpV1V2_CommName" {
                    when "not (/config_data/main/SNMP/RR_SnmpMode != 'v1_v2c_v3')";
                    type "string" {
                        pattern "[ !#%-\\)\\+-:<-\\?A-\\[\\]-_a-~]{1,32}";
                    }
                }
                leaf "RR_SnmpV3_SecUserName" {
                    when "not (/config_data/main/SNMP/RR_SnmpMode = 'Off')";
                    type "string" {
                        pattern "[!#%-\\)\\+-:<-\\?A-\\[\\]-_a-~]{0,32}";
                    }
                }
                leaf "RR_SnmpV3_EngineIdMode" {
                    when "not (/config_data/main/SNMP/RR_SnmpMode = 'Off')";
                    type "enumeration" {
                        enum "Default" {
                            value "0";
                        }
                        enum "UserDefined" {
                            value "1";
                        }
                    }
                }
                leaf "RR_SnmpInformRepeats" {
                    when "not ((/config_data/main/SNMP/RR_SnmpMode = 'Off') or (/config_data/main/SNMP/RR_SnmpNotification != 'Inform'))";
                    type "uint8" {
                        range "0..10";
                    }
                }
                leaf "RR_SnmpV3_EngineId" {
                    when "not ((/config_data/main/SNMP/RR_SnmpMode = 'Off') or (/config_data/main/SNMP/RR_SnmpV3_EngineIdMode != 'UserDefined'))";
                    type "string" {
                        pattern "[a-zA-Z0-9 _-]{0,27}";
                    }
                }
                leaf "RR_SnmpStatisticsTableUpdatePeriod" {
                    when "not (/config_data/main/SNMP/RR_SnmpMode = 'Off')";
                    type "uint16" {
                        range "1..1440";
                    }
                }
            }
            container "SnmpSecurity2" {
                when "not (/config_data/main/SNMP/RR_SnmpMode = 'Off')";
                description "Cnf. group for SNMP: security";
                leaf "RR_SnmpV3_AuthProtocol" {
                    when "not (/config_data/main/SNMP/RR_SnmpV3_SecLevel = 'NoAuthNoPriv')";
                    type "enumeration" {
                        enum "MD5_legacy" {
                            value "0";
                        }
                        enum "SHA1_legacy" {
                            value "1";
                        }
                        enum "SHA224" {
                            value "2";
                        }
                        enum "SHA256" {
                            value "3";
                        }
                        enum "SHA384" {
                            value "4";
                        }
                        enum "SHA512" {
                            value "5";
                        }
                    }
                }
                leaf "RR_SnmpV3_EncrProtocol" {
                    when "not (/config_data/main/SNMP/RR_SnmpV3_SecLevel != 'AuthPriv')";
                    type "enumeration" {
                        enum "DES_legacy" {
                            value "0";
                        }
                        enum "AES128" {
                            value "1";
                        }
                        enum "AES192" {
                            value "2";
                        }
                        enum "AES256" {
                            value "3";
                        }
                    }
                }
                leaf "RR_SnmpV3_AuthPassphrase" {
                    when "not (/config_data/main/SNMP/RR_SnmpV3_SecLevel = 'NoAuthNoPriv')";
                    type "string" {
                        pattern "(|[^\"`\\\\$;]{8,128})";
                    }
                }
                leaf "RR_SnmpV3_EncrPassphrase" {
                    when "not (/config_data/main/SNMP/RR_SnmpV3_SecLevel != 'AuthPriv')";
                    type "string" {
                        pattern "(|[^\"`\\\\$;]{8,128})";
                    }
                }
            }
            container "SyslogRmt" {
                leaf "RR_SyslogRmt_Enable" {
                    type "lbox_off_on";
                }
                leaf "RR_SyslogRmt_MaxSeverity" {
                    when "not (/config_data/main/SyslogRmt/RR_SyslogRmt_Enable != 'On')";
                    type "lbox_event_severity_error_down";
                    must "not ((. = 'Warning' and (/config_data/auth/CnfAuth/RR_CnfAuthCnfVersion >= 0)) or (. = 'Notice' and (/config_data/auth/CnfAuth/RR_CnfAuthCnfVersion >= 0)) or (. = 'Informational' and (/config_data/auth/CnfAuth/RR_CnfAuthCnfVersion >= 0)) or (. = 'Debug' and (/config_data/auth/CnfAuth/RR_CnfAuthCnfVersion >= 0)))";
                }
                leaf "RR_SyslogRmt_EventsEnable" {
                    type "lbox_off_on";
                }
                leaf "RR_SyslogRmt_EventsMaxSeverity" {
                    when "not (/config_data/main/SyslogRmt/RR_SyslogRmt_EventsEnable != 'On')";
                    type "lbox_event_severity_info_down";
                    must "not ((. = 'Debug' and (/config_data/auth/CnfAuth/RR_CnfAuthCnfVersion >= 0)))";
                }
                leaf "RR_SyslogRmt_EventsFacility" {
                    when "not (/config_data/main/SyslogRmt/RR_SyslogRmt_EventsEnable != 'On')";
                    type "enumeration" {
                        enum "LB_events_facility_Local0" {
                            value "0";
                        }
                        enum "LB_events_facility_Local1" {
                            value "1";
                        }
                        enum "LB_events_facility_Local2" {
                            value "2";
                        }
                        enum "LB_events_facility_Local3" {
                            value "3";
                        }
                        enum "LB_events_facility_Local4" {
                            value "4";
                        }
                        enum "LB_events_facility_Local5" {
                            value "5";
                        }
                        enum "LB_events_facility_Local6" {
                            value "6";
                        }
                        enum "LB_events_facility_Local7" {
                            value "7";
                        }
                    }
                }
                leaf "RR_SyslogRmt_TransportProtocol" {
                    when "not ((/config_data/main/SyslogRmt/RR_SyslogRmt_Enable != 'On') and (/config_data/main/SyslogRmt/RR_SyslogRmt_EventsEnable != 'On'))";
                    type "lbox_transport_protocol";
                }
                leaf "RR_SyslogRmt_TcpKeepaliveEnable" {
                    when "not (((/config_data/main/SyslogRmt/RR_SyslogRmt_Enable != 'On') and (/config_data/main/SyslogRmt/RR_SyslogRmt_EventsEnable != 'On')) or (/config_data/main/SyslogRmt/RR_SyslogRmt_TransportProtocol != 'LB_transport_protocol_Tcp'))";
                    type "lbox_off_on";
                }
                leaf "RR_SyslogRmt_TcpKeepaliveProbes" {
                    when "not (((/config_data/main/SyslogRmt/RR_SyslogRmt_Enable != 'On') and (/config_data/main/SyslogRmt/RR_SyslogRmt_EventsEnable != 'On')) or (/config_data/main/SyslogRmt/RR_SyslogRmt_TransportProtocol != 'LB_transport_protocol_Tcp') or (/config_data/main/SyslogRmt/RR_SyslogRmt_TcpKeepaliveEnable != 'On'))";
                    type "uint8" {
                        range "1..15";
                    }
                }
                leaf "RR_SyslogRmt_FacilitiesAll" {
                    when "not (/config_data/main/SyslogRmt/RR_SyslogRmt_Enable != 'On')";
                    type "lbox_off_on";
                }
                leaf "RR_SyslogRmt_FacilityLocal0" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityLocal1" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityLocal2" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityLocal3" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityLocal4" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityLocal5" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityLocal6" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityLocal7" {
                    when "not ((/config_data/main/SyslogRmt/RR_SyslogRmt_Enable != 'On') or (/config_data/main/SyslogRmt/RR_SyslogRmt_FacilitiesAll != 'Off'))";
                    type "lbox_off_on";
                }
                leaf "RR_SyslogRmt_TcpKeepaliveIntvl" {
                    when "not (((/config_data/main/SyslogRmt/RR_SyslogRmt_Enable != 'On') and (/config_data/main/SyslogRmt/RR_SyslogRmt_EventsEnable != 'On')) or (/config_data/main/SyslogRmt/RR_SyslogRmt_TransportProtocol != 'LB_transport_protocol_Tcp') or (/config_data/main/SyslogRmt/RR_SyslogRmt_TcpKeepaliveEnable != 'On'))";
                    type "uint8" {
                        range "10..240";
                    }
                }
                leaf "RR_SyslogRmt_TcpKeepaliveTime" {
                    when "not (((/config_data/main/SyslogRmt/RR_SyslogRmt_Enable != 'On') and (/config_data/main/SyslogRmt/RR_SyslogRmt_EventsEnable != 'On')) or (/config_data/main/SyslogRmt/RR_SyslogRmt_TransportProtocol != 'LB_transport_protocol_Tcp') or (/config_data/main/SyslogRmt/RR_SyslogRmt_TcpKeepaliveEnable != 'On'))";
                    type "uint16" {
                        range "60..64800";
                    }
                }
                leaf "RR_SyslogRmt_IpAddr" {
                    when "not ((/config_data/main/SyslogRmt/RR_SyslogRmt_Enable != 'On') and (/config_data/main/SyslogRmt/RR_SyslogRmt_EventsEnable != 'On'))";
                    type "inet:ipv4-address";
                }
                leaf "RR_SyslogRmt_IpPort" {
                    when "not ((/config_data/main/SyslogRmt/RR_SyslogRmt_Enable != 'On') and (/config_data/main/SyslogRmt/RR_SyslogRmt_EventsEnable != 'On'))";
                    type "lim_udp_port";
                }
                leaf "RR_SyslogRmt_TimeReopen" {
                    when "not ((/config_data/main/SyslogRmt/RR_SyslogRmt_Enable != 'On') and (/config_data/main/SyslogRmt/RR_SyslogRmt_EventsEnable != 'On'))";
                    type "uint8" {
                        range "1..240";
                    }
                }
                leaf "RR_SyslogRmt_FacilityKernel" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityUser" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityMail" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityDaemon" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityAuth" {
                    when "not ((/config_data/main/SyslogRmt/RR_SyslogRmt_Enable != 'On') or (/config_data/main/SyslogRmt/RR_SyslogRmt_FacilitiesAll != 'Off'))";
                    type "lbox_off_on";
                }
                leaf "RR_SyslogRmt_FacilitySyslog" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityLinePrinter" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityNews" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityUucp" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityCron" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityAuthPrivate" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityFtp" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityNtp" {
                    when "not ((/config_data/main/SyslogRmt/RR_SyslogRmt_Enable != 'On') or (/config_data/main/SyslogRmt/RR_SyslogRmt_FacilitiesAll != 'Off'))";
                    type "lbox_off_on";
                }
                leaf "RR_SyslogRmt_FacilitySecurity" {
                    when "not ((/config_data/main/SyslogRmt/RR_SyslogRmt_Enable != 'On') or (/config_data/main/SyslogRmt/RR_SyslogRmt_FacilitiesAll != 'Off'))";
                    type "lbox_off_on";
                }
                leaf "RR_SyslogRmt_FacilityConsole" {
                    when "not ((/config_data/main/SyslogRmt/RR_SyslogRmt_Enable != 'On') or (/config_data/main/SyslogRmt/RR_SyslogRmt_FacilitiesAll != 'Off'))";
                    type "lbox_off_on";
                }
                leaf "RR_SyslogRmt_FacilitySolarisCron" {
                    when "not ((/config_data/main/SyslogRmt/RR_SyslogRmt_Enable != 'On') or (/config_data/main/SyslogRmt/RR_SyslogRmt_FacilitiesAll != 'Off'))";
                    type "lbox_off_on";
                }
            }
            container "HWIO" {
                leaf "RR_HWIO_AI" {
                    type "lbox_hw_io";
                }
                leaf "RR_HWIO_AO" {
                    type "lbox_hw_io";
                }
                leaf "RR_DIDO_O1" {
                    when "not (((/config_data/device/DeviceHw/RR_DynHw_HotStandby = 'On') and (/config_data/main/HotStdby/RR_HotStdby_Enable = 'On')) or (/config_data/device/DeviceHw/RR_DynHw_Port_Dido_Do_Cnt <= 0))";
                    type "lbox_hw_io";
                }
                leaf "RR_DIDO_O2" {
                    when "not (((/config_data/device/DeviceHw/RR_DynHw_HotStandby = 'On') and (/config_data/main/HotStdby/RR_HotStdby_Enable = 'On')) or (/config_data/device/DeviceHw/RR_DynHw_Port_Dido_Do_Cnt <= 1))";
                    type "lbox_hw_io";
                }
                leaf "RR_DIDO_I1" {
                    when "not (((/config_data/device/DeviceHw/RR_DynHw_HotStandby = 'On') and (/config_data/main/HotStdby/RR_HotStdby_Enable = 'On')) or (/config_data/device/DeviceHw/RR_DynHw_Port_Dido_Di_Cnt <= 0))";
                    type "lbox_hw_io";
                }
                leaf "RR_DIDO_I2" {
                    when "not (((/config_data/device/DeviceHw/RR_DynHw_HotStandby = 'On') and (/config_data/main/HotStdby/RR_HotStdby_Enable = 'On')) or (/config_data/device/DeviceHw/RR_DynHw_Port_Dido_Di_Cnt <= 1))";
                    type "lbox_hw_io";
                }
                leaf "RR_DIDO_I3" {
                    when "not (((/config_data/device/DeviceHw/RR_DynHw_HotStandby = 'On') and (/config_data/main/HotStdby/RR_HotStdby_Enable = 'On')) or (/config_data/device/DeviceHw/RR_DynHw_Port_Dido_Di_Cnt <= 2))";
                    type "lbox_hw_io";
                }
            }
            container "ComPort_1" {
                when "not (/config_data/device/DeviceHw/RR_DynHw_Port_Com1 != 'On')";
                leaf "RR_ComPort_1_Type" {
                    when "not (/config_data/main/ComPort_1/RR_ComPort_1_ENA != 'On')";
                    type "lbox_com_port_1_type_M3";
                    must "not ((. = 'RS485' and ((/config_data/device/DeviceHw/RR_DynHw_Port_Com1_Rs485 != 'On') or (/config_data/main/ComPort_1/RR_ComPort_1_Protocol = 'PPP') or ((/config_data/device/DeviceHw/RR_DynHw_Module_Board_Com = 'On') and (/config_data/main/ComPort_2/RR_ComPort_2_ENA != 'Off')))))";
                }
                leaf "RR_ComPort_1_BaudRate" {
                    when "not (/config_data/main/ComPort_1/RR_ComPort_1_ENA != 'On')";
                    type "lbox_com_port_baud_rate";
                    must "not ((. = '300 B' and (/config_data/auth/CnfAuth/RR_CnfAuthCnfVersion >= 0)))";
                }
                leaf "RR_ComPort_1_DataBits" {
                    when "not (/config_data/main/ComPort_1/RR_ComPort_1_ENA != 'On')";
                    type "lbox_com_port_1_data_bits_M2";
                    must "not ((. = '5 bits' and (/config_data/main/ComPort_1/RR_ComPort_1_Protocol = 'PPP')) or (. = '6 bits' and (/config_data/main/ComPort_1/RR_ComPort_1_Protocol = 'PPP')) or (. = '7 bits' and (/config_data/main/ComPort_1/RR_ComPort_1_Protocol = 'PPP')))";
                }
                leaf "RR_ComPort_1_Parity" {
                    when "not (/config_data/main/ComPort_1/RR_ComPort_1_ENA != 'On')";
                    type "lbox_com_port_1_parity_M2";
                    must "not ((. = 'ODD' and (/config_data/main/ComPort_1/RR_ComPort_1_Protocol = 'PPP')) or (. = 'EVEN' and (/config_data/main/ComPort_1/RR_ComPort_1_Protocol = 'PPP')))";
                }
                leaf "RR_ComPort_1_StopBits" {
                    when "not (/config_data/main/ComPort_1/RR_ComPort_1_ENA != 'On')";
                    type "lbox_com_port_1_stop_bits_M1";
                }
                leaf "RR_ComPort_1_MRU" {
                    when "not (/config_data/main/ComPort_1/RR_ComPort_1_ENA != 'On')";
                    type "uint16" {
                        range "1..2047";
                    }
                }
                leaf "RR_ComPort_1_ENA" {
                    type "lbox_off_on";
                }
                leaf "RR_ComPort_1_FlowControl" {
                    when "not (/config_data/main/ComPort_1/RR_ComPort_1_ENA != 'On')";
                    type "lbox_com_port_1_flow_ctrl_M3";
                    must "not ((. = 'RTS/CTS' and ((/config_data/device/DeviceHw/RR_DynHw_Sig_RtsCts_Com1 != 'On') or (/config_data/main/ComPort_1/RR_ComPort_1_Type != 'RS232') or ((/config_data/device/DeviceHw/RR_DynHw_Primary_Cellular = 'On') and (/config_data/device/DeviceHw/RR_DynHw_Module_Board_Com = 'On') and (/config_data/main/ComPort_2/RR_ComPort_2_ENA != 'Off')))))";
                }
                leaf "RR_ComPort_1_Protocol" {
                    when "not (/config_data/main/ComPort_1/RR_ComPort_1_ENA != 'On')";
                    type "lbox_protocols_COM_M9";
                    must "not ((. = 'Transparent' and ((/config_data/device/DeviceHw/RR_DynHw_Primary_Radio != 'On') or (/config_data/main/RadioInterface/RR_RadioIfMode != 'Bridge'))))";
                }
                leaf "RR_ComPort_1_Idles" {
                    when "not ((/config_data/main/ComPort_1/RR_ComPort_1_ENA != 'On') or (/config_data/main/ComPort_1/RR_ComPort_1_Protocol = 'PPP'))";
                    type "uint16" {
                        range "10..16383";
                    }
                }
                leaf "RR_ComPort_1_ProtResetTimeout" {
                    when "not (/config_data/main/ComPort_1/RR_ComPort_1_ENA != 'On')";
                    type "uint16" {
                        range "0..65535";
                    }
                }
            }
            container "ComPort_2" {
                when "not (/config_data/device/DeviceHw/RR_DynHw_Port_Com2 != 'On')";
                leaf "RR_ComPort_2_BaudRateSpec" {
                    when "not (/config_data/main/ComPort_2/RR_ComPort_2_ENA != 'On')";
                    type "lbox_com_port_2_baud_rate";
                }
                leaf "RR_ComPort_2_DataBits" {
                    when "not (/config_data/main/ComPort_2/RR_ComPort_2_ENA != 'On')";
                    type "lbox_com_port_2_data_bits_M2";
                    must "not ((. = '5 bits' and (/config_data/main/ComPort_2/RR_ComPort_2_Protocol = 'PPP')) or (. = '6 bits' and (/config_data/main/ComPort_2/RR_ComPort_2_Protocol = 'PPP')) or (. = '7 bits' and (/config_data/main/ComPort_2/RR_ComPort_2_Protocol = 'PPP')))";
                }
                leaf "RR_ComPort_2_Parity" {
                    when "not (/config_data/main/ComPort_2/RR_ComPort_2_ENA != 'On')";
                    type "lbox_com_port_2_parity_M2";
                    must "not ((. = 'ODD' and (/config_data/main/ComPort_2/RR_ComPort_2_Protocol = 'PPP')) or (. = 'EVEN' and (/config_data/main/ComPort_2/RR_ComPort_2_Protocol = 'PPP')))";
                }
                leaf "RR_ComPort_2_StopBits" {
                    when "not (/config_data/main/ComPort_2/RR_ComPort_2_ENA != 'On')";
                    type "lbox_com_port_2_stop_bits_M1";
                }
                leaf "RR_ComPort_2_MRU" {
                    when "not (/config_data/main/ComPort_2/RR_ComPort_2_ENA != 'On')";
                    type "uint16" {
                        range "1..2047";
                    }
                }
                leaf "RR_ComPort_2_ENA" {
                    type "enumeration" {
                        enum "Off" {
                            value "0";
                        }
                        enum "On" {
                            value "1";
                        }
                    }
                    must "not ((. = 'On' and ((/config_data/device/DeviceHw/RR_DynHw_Module_Board_Com = 'On') and (/config_data/device/DeviceSwKey/RR_SwKey_Flag_interface_db9_com2 != 'On'))))";
                }
                leaf "RR_ComPort_2_FlowControl" {
                    when "not (/config_data/main/ComPort_2/RR_ComPort_2_ENA != 'On')";
                    type "lbox_com_port_2_flow_ctrl_M1";
                    must "not ((. = 'RTS/CTS' and (/config_data/device/DeviceHw/RR_DynHw_Sig_RtsCts_Com2 != 'On')))";
                }
                leaf "RR_ComPort_2_Protocol" {
                    when "not (/config_data/main/ComPort_2/RR_ComPort_2_ENA != 'On')";
                    type "lbox_protocols_COM_M9";
                    must "not ((. = 'Transparent' and ((/config_data/device/DeviceHw/RR_DynHw_Primary_Radio != 'On') or (/config_data/main/RadioInterface/RR_RadioIfMode != 'Bridge'))))";
                }
                leaf "RR_ComPort_2_Idles" {
                    when "not ((/config_data/main/ComPort_2/RR_ComPort_2_ENA != 'On') or (/config_data/main/ComPort_2/RR_ComPort_2_Protocol = 'PPP'))";
                    type "uint16" {
                        range "10..16383";
                    }
                }
                leaf "RR_ComPort_2_ProtResetTimeout" {
                    when "not (/config_data/main/ComPort_2/RR_ComPort_2_ENA != 'On')";
                    type "uint16" {
                        range "0..65535";
                    }
                }
            }
            container "ComPort_3" {
                when "not (/config_data/device/DeviceHw/RR_DynHw_Port_Com3 != 'On')";
                leaf "RR_ComPort_3_BaudRateSpec" {
                    when "not (/config_data/main/ComPort_3/RR_ComPort_3_ENA != 'On')";
                    type "lbox_com_port_3_baud_rate";
                }
                leaf "RR_ComPort_3_DataBits" {
                    when "not (/config_data/main/ComPort_3/RR_ComPort_3_ENA != 'On')";
                    type "lbox_com_port_3_data_bits_M2";
                }
                leaf "RR_ComPort_3_Parity" {
                    when "not (/config_data/main/ComPort_3/RR_ComPort_3_ENA != 'On')";
                    type "lbox_com_port_3_parity_M2";
                    must "not ((. = 'ODD' and (/config_data/main/ComPort_3/RR_ComPort_3_Protocol = 'PPP')) or (. = 'EVEN' and (/config_data/main/ComPort_3/RR_ComPort_3_Protocol = 'PPP')))";
                }
                leaf "RR_ComPort_3_StopBits" {
                    when "not (/config_data/main/ComPort_3/RR_ComPort_3_ENA != 'On')";
                    type "lbox_com_port_3_stop_bits_M1";
                }
                leaf "RR_ComPort_3_MRU" {
                    when "not (/config_data/main/ComPort_3/RR_ComPort_3_ENA != 'On')";
                    type "uint16" {
                        range "1..2047";
                    }
                }
                leaf "RR_ComPort_3_ENA" {
                    type "lbox_off_on";
                }
                leaf "RR_ComPort_3_Protocol" {
                    when "not (/config_data/main/ComPort_3/RR_ComPort_3_ENA != 'On')";
                    type "lbox_protocols_COM_M9";
                    must "not ((. = 'Transparent' and ((/config_data/device/DeviceHw/RR_DynHw_Primary_Radio != 'On') or (/config_data/main/RadioInterface/RR_RadioIfMode != 'Bridge'))))";
                }
                leaf "RR_ComPort_3_Idles" {
                    when "not ((/config_data/main/ComPort_3/RR_ComPort_3_ENA != 'On') or (/config_data/main/ComPort_3/RR_ComPort_3_Protocol = 'PPP'))";
                    type "uint16" {
                        range "10..16383";
                    }
                }
                leaf "RR_ComPort_3_ProtResetTimeout" {
                    when "not (/config_data/main/ComPort_3/RR_ComPort_3_ENA != 'On')";
                    type "uint16" {
                        range "0..65535";
                    }
                }
            }
            container "TerminalServer_1" {
                leaf "RR_TerminalServer_1_ENA" {
                    type "lbox_off_on";
                }
                leaf "RR_TerminalServer_1_Type" {
                    when "not (/config_data/main/TerminalServer_1/RR_TerminalServer_1_ENA != 'On')";
                    type "lbox_term_server_type";
                }
                leaf "RR_TerminalServer_1_TCPInact" {
                    when "not ((/config_data/main/TerminalServer_1/RR_TerminalServer_1_ENA != 'On') or (/config_data/main/TerminalServer_1/RR_TerminalServer_1_Type != 'TCP'))";
                    type "lim_uint_8";
                }
                leaf "RR_TerminalServer_1_DstIp" {
                    when "not (/config_data/main/TerminalServer_1/RR_TerminalServer_1_ENA != 'On')";
                    type "inet:ipv4-address";
                }
                leaf "RR_TerminalServer_1_DstPort" {
                    when "not (/config_data/main/TerminalServer_1/RR_TerminalServer_1_ENA != 'On')";
                    type "lim_udp_port0";
                }
                leaf "RR_TerminalServer_1_ProtPort" {
                    when "not (/config_data/main/TerminalServer_1/RR_TerminalServer_1_ENA != 'On')";
                    type "lim_udp_port0";
                }
                leaf "RR_TerminalServer_1_Protocol" {
                    when "not (/config_data/main/TerminalServer_1/RR_TerminalServer_1_ENA != 'On')";
                    type "lbox_protocols_M8";
                    must "not ((. = 'Transparent' and ((/config_data/device/DeviceHw/RR_DynHw_Primary_Radio != 'On') or (/config_data/main/RadioInterface/RR_RadioIfMode != 'Bridge'))))";
                }
                leaf "RR_TerminalServer_1_ProtResetTimeout" {
                    when "not (/config_data/main/TerminalServer_1/RR_TerminalServer_1_ENA != 'On')";
                    type "uint16" {
                        range "0..65535";
                    }
                }
            }
            container "TerminalServer_2" {
                leaf "RR_TerminalServer_2_ENA" {
                    type "lbox_off_on";
                }
                leaf "RR_TerminalServer_2_Type" {
                    when "not (/config_data/main/TerminalServer_2/RR_TerminalServer_2_ENA != 'On')";
                    type "lbox_term_server_type";
                }
                leaf "RR_TerminalServer_2_TCPInact" {
                    when "not ((/config_data/main/TerminalServer_2/RR_TerminalServer_2_ENA != 'On') or (/config_data/main/TerminalServer_2/RR_TerminalServer_2_Type != 'TCP'))";
                    type "lim_uint_8";
                }
                leaf "RR_TerminalServer_2_DstIp" {
                    when "not (/config_data/main/TerminalServer_2/RR_TerminalServer_2_ENA != 'On')";
                    type "inet:ipv4-address";
                }
                leaf "RR_TerminalServer_2_DstPort" {
                    when "not (/config_data/main/TerminalServer_2/RR_TerminalServer_2_ENA != 'On')";
                    type "lim_udp_port0";
                }
                leaf "RR_TerminalServer_2_ProtPort" {
                    when "not (/config_data/main/TerminalServer_2/RR_TerminalServer_2_ENA != 'On')";
                    type "lim_udp_port0";
                }
                leaf "RR_TerminalServer_2_Protocol" {
                    when "not (/config_data/main/TerminalServer_2/RR_TerminalServer_2_ENA != 'On')";
                    type "lbox_protocols_M8";
                    must "not ((. = 'Transparent' and ((/config_data/device/DeviceHw/RR_DynHw_Primary_Radio != 'On') or (/config_data/main/RadioInterface/RR_RadioIfMode != 'Bridge'))))";
                }
                leaf "RR_TerminalServer_2_ProtResetTimeout" {
                    when "not (/config_data/main/TerminalServer_2/RR_TerminalServer_2_ENA != 'On')";
                    type "uint16" {
                        range "0..65535";
                    }
                }
            }
            container "TerminalServer_3" {
                leaf "RR_TerminalServer_3_ENA" {
                    type "lbox_off_on";
                }
                leaf "RR_TerminalServer_3_Type" {
                    when "not (/config_data/main/TerminalServer_3/RR_TerminalServer_3_ENA != 'On')";
                    type "lbox_term_server_type";
                }
                leaf "RR_TerminalServer_3_TCPInact" {
                    when "not ((/config_data/main/TerminalServer_3/RR_TerminalServer_3_ENA != 'On') or (/config_data/main/TerminalServer_3/RR_TerminalServer_3_Type != 'TCP'))";
                    type "lim_uint_8";
                }
                leaf "RR_TerminalServer_3_DstIp" {
                    when "not (/config_data/main/TerminalServer_3/RR_TerminalServer_3_ENA != 'On')";
                    type "inet:ipv4-address";
                }
                leaf "RR_TerminalServer_3_DstPort" {
                    when "not (/config_data/main/TerminalServer_3/RR_TerminalServer_3_ENA != 'On')";
                    type "lim_udp_port0";
                }
                leaf "RR_TerminalServer_3_ProtPort" {
                    when "not (/config_data/main/TerminalServer_3/RR_TerminalServer_3_ENA != 'On')";
                    type "lim_udp_port0";
                }
                leaf "RR_TerminalServer_3_Protocol" {
                    when "not (/config_data/main/TerminalServer_3/RR_TerminalServer_3_ENA != 'On')";
                    type "lbox_protocols_M8";
                    must "not ((. = 'Transparent' and ((/config_data/device/DeviceHw/RR_DynHw_Primary_Radio != 'On') or (/config_data/main/RadioInterface/RR_RadioIfMode != 'Bridge'))))";
                }
                leaf "RR_TerminalServer_3_ProtResetTimeout" {
                    when "not (/config_data/main/TerminalServer_3/RR_TerminalServer_3_ENA != 'On')";
                    type "uint16" {
                        range "0..65535";
                    }
                }
            }
            container "TerminalServer_4" {
                leaf "RR_TerminalServer_4_ENA" {
                    type "lbox_off_on";
                }
                leaf "RR_TerminalServer_4_Type" {
                    when "not (/config_data/main/TerminalServer_4/RR_TerminalServer_4_ENA != 'On')";
                    type "lbox_term_server_type";
                }
                leaf "RR_TerminalServer_4_TCPInact" {
                    when "not ((/config_data/main/TerminalServer_4/RR_TerminalServer_4_ENA != 'On') or (/config_data/main/TerminalServer_4/RR_TerminalServer_4_Type != 'TCP'))";
                    type "lim_uint_8";
                }
                leaf "RR_TerminalServer_4_DstIp" {
                    when "not (/config_data/main/TerminalServer_4/RR_TerminalServer_4_ENA != 'On')";
                    type "inet:ipv4-address";
                }
                leaf "RR_TerminalServer_4_DstPort" {
                    when "not (/config_data/main/TerminalServer_4/RR_TerminalServer_4_ENA != 'On')";
                    type "lim_udp_port0";
                }
                leaf "RR_TerminalServer_4_ProtPort" {
                    when "not (/config_data/main/TerminalServer_4/RR_TerminalServer_4_ENA != 'On')";
                    type "lim_udp_port0";
                }
                leaf "RR_TerminalServer_4_Protocol" {
                    when "not (/config_data/main/TerminalServer_4/RR_TerminalServer_4_ENA != 'On')";
                    type "lbox_protocols_M8";
                    must "not ((. = 'Transparent' and ((/config_data/device/DeviceHw/RR_DynHw_Primary_Radio != 'On') or (/config_data/main/RadioInterface/RR_RadioIfMode != 'Bridge'))))";
                }
                leaf "RR_TerminalServer_4_ProtResetTimeout" {
                    when "not (/config_data/main/TerminalServer_4/RR_TerminalServer_4_ENA != 'On')";
                    type "uint16" {
                        range "0..65535";
                    }
                }
            }
            container "TerminalServer_5" {
                leaf "RR_TerminalServer_5_ENA" {
                    type "lbox_off_on";
                }
                leaf "RR_TerminalServer_5_Type" {
                    when "not (/config_data/main/TerminalServer_5/RR_TerminalServer_5_ENA != 'On')";
                    type "lbox_term_server_type";
                }
                leaf "RR_TerminalServer_5_TCPInact" {
                    when "not ((/config_data/main/TerminalServer_5/RR_TerminalServer_5_ENA != 'On') or (/config_data/main/TerminalServer_5/RR_TerminalServer_5_Type != 'TCP'))";
                    type "lim_uint_8";
                }
                leaf "RR_TerminalServer_5_DstIp" {
                    when "not (/config_data/main/TerminalServer_5/RR_TerminalServer_5_ENA != 'On')";
                    type "inet:ipv4-address";
                }
                leaf "RR_TerminalServer_5_DstPort" {
                    when "not (/config_data/main/TerminalServer_5/RR_TerminalServer_5_ENA != 'On')";
                    type "lim_udp_port0";
                }
                leaf "RR_TerminalServer_5_ProtPort" {
                    when "not (/config_data/main/TerminalServer_5/RR_TerminalServer_5_ENA != 'On')";
                    type "lim_udp_port0";
                }
                leaf "RR_TerminalServer_5_Protocol" {
                    when "not (/config_data/main/TerminalServer_5/RR_TerminalServer_5_ENA != 'On')";
                    type "lbox_protocols_M8";
                    must "not ((. = 'Transparent' and ((/config_data/device/DeviceHw/RR_DynHw_Primary_Radio != 'On') or (/config_data/main/RadioInterface/RR_RadioIfMode != 'Bridge'))))";
                }
                leaf "RR_TerminalServer_5_ProtResetTimeout" {
                    when "not (/config_data/main/TerminalServer_5/RR_TerminalServer_5_ENA != 'On')";
                    type "uint16" {
                        range "0..65535";
                    }
                }
            }
            container "SvcAccess" {
                leaf "RR_SvcAcc_UsbEthEn" {
                    type "lbox_off_on";
                }
                leaf "RR_SvcAcc_UsbWifiEn" {
                    type "lbox_off_on";
                }
                leaf "RR_SvcAcc_IpMask" {
                    when "not ((/config_data/main/SvcAccess/RR_SvcAcc_UsbEthEn != 'On') and (/config_data/main/SvcAccess/RR_SvcAcc_UsbWifiEn != 'On'))";
                    type "lim_ipv4_mask";
                }
                leaf "RR_SvcAcc_IpAddr" {
                    when "not ((/config_data/main/SvcAccess/RR_SvcAcc_UsbEthEn != 'On') and (/config_data/main/SvcAccess/RR_SvcAcc_UsbWifiEn != 'On'))";
                    type "inet:ipv4-address";
                }
                leaf "RR_SvcAcc_DhcpStartIp" {
                    when "not ((/config_data/main/SvcAccess/RR_SvcAcc_UsbEthEn != 'On') and (/config_data/main/SvcAccess/RR_SvcAcc_UsbWifiEn != 'On'))";
                    type "inet:ipv4-address";
                    must "(round(16777216 * number(substring-before(., \".\")) + 65536 * number(substring-before(substring-after(., \".\"), \".\")) + 256 * number(substring-before(substring-after(substring-after(., \".\"), \".\"), \".\")) + number(substring-after(substring-after(substring-after(., \".\"), \".\"), \".\")))) <= (round(16777216 * number(substring-before(/config_data/main/SvcAccess/RR_SvcAcc_DhcpEndIp, \".\")) + 65536 * number(substring-before(substring-after(/config_data/main/SvcAccess/RR_SvcAcc_DhcpEndIp, \".\"), \".\")) + 256 * number(substring-before(substring-after(substring-after(/config_data/main/SvcAccess/RR_SvcAcc_DhcpEndIp, \".\"), \".\"), \".\")) + number(substring-after(substring-after(substring-after(/config_data/main/SvcAccess/RR_SvcAcc_DhcpEndIp, \".\"), \".\"), \".\"))))" {
                        error-message "valmsg_it_SvcAcc_DhcpStartIp";
                    }
                }
                leaf "RR_SvcAcc_DhcpEndIp" {
                    when "not ((/config_data/main/SvcAccess/RR_SvcAcc_UsbEthEn != 'On') and (/config_data/main/SvcAccess/RR_SvcAcc_UsbWifiEn != 'On'))";
                    type "inet:ipv4-address";
                    must "(round(16777216 * number(substring-before(., \".\")) + 65536 * number(substring-before(substring-after(., \".\"), \".\")) + 256 * number(substring-before(substring-after(substring-after(., \".\"), \".\"), \".\")) + number(substring-after(substring-after(substring-after(., \".\"), \".\"), \".\")))) >= (round(16777216 * number(substring-before(/config_data/main/SvcAccess/RR_SvcAcc_DhcpStartIp, \".\")) + 65536 * number(substring-before(substring-after(/config_data/main/SvcAccess/RR_SvcAcc_DhcpStartIp, \".\"), \".\")) + 256 * number(substring-before(substring-after(substring-after(/config_data/main/SvcAccess/RR_SvcAcc_DhcpStartIp, \".\"), \".\"), \".\")) + number(substring-after(substring-after(substring-after(/config_data/main/SvcAccess/RR_SvcAcc_DhcpStartIp, \".\"), \".\"), \".\"))))" {
                        error-message "valmsg_it_SvcAcc_DhcpEndIp";
                    }
                }
            }
            container "SvcAccessWifi" {
                when "not (/config_data/main/SvcAccess/RR_SvcAcc_UsbWifiEn != 'On')";
                leaf "RR_SvcWifi_SsidAutomatic" {
                    type "lbox_off_on";
                }
                leaf "RR_SvcWifi_Mode" {
                    type "enumeration" {
                        enum "802.11g" {
                            value "0";
                        }
                        enum "802.11n" {
                            value "1";
                        }
                    }
                }
                leaf "RR_SvcWifi_Channel" {
                    type "enumeration" {
                        enum "1 - 2412 MHz" {
                            value "1";
                        }
                        enum "2 - 2417 MHz" {
                            value "2";
                        }
                        enum "3 - 2422 MHz" {
                            value "3";
                        }
                        enum "4 - 2427 MHz" {
                            value "4";
                        }
                        enum "5 - 2432 MHz" {
                            value "5";
                        }
                        enum "6 - 2437 MHz" {
                            value "6";
                        }
                        enum "7 - 2442 MHz" {
                            value "7";
                        }
                        enum "8 - 2447 MHz" {
                            value "8";
                        }
                        enum "9 - 2452 MHz" {
                            value "9";
                        }
                        enum "10 - 2457 MHz" {
                            value "10";
                        }
                        enum "11 - 2462 MHz" {
                            value "11";
                        }
                    }
                    must "not ((. = '8 - 2447 MHz' and (/config_data/main/SvcAccessWifi/RR_SvcWifi_Mode = '802.11n')) or (. = '9 - 2452 MHz' and (/config_data/main/SvcAccessWifi/RR_SvcWifi_Mode = '802.11n')) or (. = '10 - 2457 MHz' and (/config_data/main/SvcAccessWifi/RR_SvcWifi_Mode = '802.11n')) or (. = '11 - 2462 MHz' and (/config_data/main/SvcAccessWifi/RR_SvcWifi_Mode = '802.11n')))";
                }
                leaf "RR_SvcWifi_Security" {
                    type "enumeration" {
                        enum "Off" {
                            value "0";
                        }
                        enum "WPA2-PSK" {
                            value "1";
                        }
                    }
                }
                leaf "RR_SvcWifi_Ssid" {
                    when "not (/config_data/main/SvcAccessWifi/RR_SvcWifi_SsidAutomatic = 'On')";
                    type "string" {
                        pattern "[^\"`\\\\$;]{1,32}";
                    }
                }
                leaf "RR_SvcWifi_Passphrase" {
                    when "not (/config_data/main/SvcAccessWifi/RR_SvcWifi_Security = 'Off')";
                    type "string" {
                        pattern "[^\"`\\\\$;]{0,63}";
                    }
                }
            }
            container "Time" {
                leaf "RR_Time_GnssSynchEn" {
                    when "not ((/config_data/device/DeviceHw/RR_DynHw_Module_Gps = 'Off') or (/config_data/main/Gnss/RR_Gnss_Enable = 'Off'))";
                    type "lbox_off_on";
                }
                leaf "RR_Time_NtpMinPoll" {
                    type "enumeration" {
                        enum "1 min." {
                            value "0";
                        }
                        enum "2 min." {
                            value "1";
                        }
                        enum "4 min." {
                            value "2";
                        }
                        enum "8.5 min." {
                            value "3";
                        }
                        enum "17 min." {
                            value "4";
                        }
                        enum "34 min." {
                            value "5";
                        }
                        enum "1 h 8 min." {
                            value "6";
                        }
                        enum "2 h 17 min." {
                            value "7";
                        }
                    }
                }
                leaf "RR_Time_TZone" {
                    type "enumeration" {
                        enum "Etc/UTC" {
                            value "0";
                        }
                        enum "Africa/Abidjan" {
                            value "1";
                        }
                        enum "Africa/Accra" {
                            value "2";
                        }
                        enum "Africa/Algiers" {
                            value "3";
                        }
                        enum "Africa/Bissau" {
                            value "4";
                        }
                        enum "Africa/Cairo" {
                            value "5";
                        }
                        enum "Africa/Casablanca" {
                            value "6";
                        }
                        enum "Africa/Ceuta" {
                            value "7";
                        }
                        enum "Africa/El_Aaiun" {
                            value "8";
                        }
                        enum "Africa/Johannesburg" {
                            value "9";
                        }
                        enum "Africa/Juba" {
                            value "10";
                        }
                        enum "Africa/Khartoum" {
                            value "11";
                        }
                        enum "Africa/Lagos" {
                            value "12";
                        }
                        enum "Africa/Maputo" {
                            value "13";
                        }
                        enum "Africa/Monrovia" {
                            value "14";
                        }
                        enum "Africa/Nairobi" {
                            value "15";
                        }
                        enum "Africa/Ndjamena" {
                            value "16";
                        }
                        enum "Africa/Sao_Tome" {
                            value "17";
                        }
                        enum "Africa/Tripoli" {
                            value "18";
                        }
                        enum "Africa/Tunis" {
                            value "19";
                        }
                        enum "Africa/Windhoek" {
                            value "20";
                        }
                        enum "America/Adak" {
                            value "21";
                        }
                        enum "America/Anchorage" {
                            value "22";
                        }
                        enum "America/Araguaina" {
                            value "23";
                        }
                        enum "America/Argentina/Buenos_Aires" {
                            value "24";
                        }
                        enum "America/Argentina/Catamarca" {
                            value "25";
                        }
                        enum "America/Argentina/Cordoba" {
                            value "26";
                        }
                        enum "America/Argentina/Jujuy" {
                            value "27";
                        }
                        enum "America/Argentina/La_Rioja" {
                            value "28";
                        }
                        enum "America/Argentina/Mendoza" {
                            value "29";
                        }
                        enum "America/Argentina/Rio_Gallegos" {
                            value "30";
                        }
                        enum "America/Argentina/Salta" {
                            value "31";
                        }
                        enum "America/Argentina/San_Juan" {
                            value "32";
                        }
                        enum "America/Argentina/San_Luis" {
                            value "33";
                        }
                        enum "America/Argentina/Tucuman" {
                            value "34";
                        }
                        enum "America/Argentina/Ushuaia" {
                            value "35";
                        }
                        enum "America/Asuncion" {
                            value "36";
                        }
                        enum "America/Atikokan" {
                            value "37";
                        }
                        enum "America/Bahia" {
                            value "38";
                        }
                        enum "America/Bahia_Banderas" {
                            value "39";
                        }
                        enum "America/Barbados" {
                            value "40";
                        }
                        enum "America/Belem" {
                            value "41";
                        }
                        enum "America/Belize" {
                            value "42";
                        }
                        enum "America/Blanc-Sablon" {
                            value "43";
                        }
                        enum "America/Boa_Vista" {
                            value "44";
                        }
                        enum "America/Bogota" {
                            value "45";
                        }
                        enum "America/Boise" {
                            value "46";
                        }
                        enum "America/Cambridge_Bay" {
                            value "47";
                        }
                        enum "America/Campo_Grande" {
                            value "48";
                        }
                        enum "America/Cancun" {
                            value "49";
                        }
                        enum "America/Caracas" {
                            value "50";
                        }
                        enum "America/Cayenne" {
                            value "51";
                        }
                        enum "America/Chicago" {
                            value "52";
                        }
                        enum "America/Chihuahua" {
                            value "53";
                        }
                        enum "America/Costa_Rica" {
                            value "54";
                        }
                        enum "America/Creston" {
                            value "55";
                        }
                        enum "America/Cuiaba" {
                            value "56";
                        }
                        enum "America/Curacao" {
                            value "57";
                        }
                        enum "America/Danmarkshavn" {
                            value "58";
                        }
                        enum "America/Dawson" {
                            value "59";
                        }
                        enum "America/Dawson_Creek" {
                            value "60";
                        }
                        enum "America/Denver" {
                            value "61";
                        }
                        enum "America/Detroit" {
                            value "62";
                        }
                        enum "America/Edmonton" {
                            value "63";
                        }
                        enum "America/Eirunepe" {
                            value "64";
                        }
                        enum "America/El_Salvador" {
                            value "65";
                        }
                        enum "America/Fortaleza" {
                            value "66";
                        }
                        enum "America/Fort_Nelson" {
                            value "67";
                        }
                        enum "America/Glace_Bay" {
                            value "68";
                        }
                        enum "America/Goose_Bay" {
                            value "69";
                        }
                        enum "America/Grand_Turk" {
                            value "70";
                        }
                        enum "America/Guatemala" {
                            value "71";
                        }
                        enum "America/Guayaquil" {
                            value "72";
                        }
                        enum "America/Guyana" {
                            value "73";
                        }
                        enum "America/Halifax" {
                            value "74";
                        }
                        enum "America/Havana" {
                            value "75";
                        }
                        enum "America/Hermosillo" {
                            value "76";
                        }
                        enum "America/Indiana/Indianapolis" {
                            value "77";
                        }
                        enum "America/Indiana/Knox" {
                            value "78";
                        }
                        enum "America/Indiana/Marengo" {
                            value "79";
                        }
                        enum "America/Indiana/Petersburg" {
                            value "80";
                        }
                        enum "America/Indiana/Tell_City" {
                            value "81";
                        }
                        enum "America/Indiana/Vevay" {
                            value "82";
                        }
                        enum "America/Indiana/Vincennes" {
                            value "83";
                        }
                        enum "America/Indiana/Winamac" {
                            value "84";
                        }
                        enum "America/Inuvik" {
                            value "85";
                        }
                        enum "America/Iqaluit" {
                            value "86";
                        }
                        enum "America/Jamaica" {
                            value "87";
                        }
                        enum "America/Juneau" {
                            value "88";
                        }
                        enum "America/Kentucky/Louisville" {
                            value "89";
                        }
                        enum "America/Kentucky/Monticello" {
                            value "90";
                        }
                        enum "America/La_Paz" {
                            value "91";
                        }
                        enum "America/Lima" {
                            value "92";
                        }
                        enum "America/Los_Angeles" {
                            value "93";
                        }
                        enum "America/Maceio" {
                            value "94";
                        }
                        enum "America/Managua" {
                            value "95";
                        }
                        enum "America/Manaus" {
                            value "96";
                        }
                        enum "America/Martinique" {
                            value "97";
                        }
                        enum "America/Matamoros" {
                            value "98";
                        }
                        enum "America/Mazatlan" {
                            value "99";
                        }
                        enum "America/Menominee" {
                            value "100";
                        }
                        enum "America/Merida" {
                            value "101";
                        }
                        enum "America/Metlakatla" {
                            value "102";
                        }
                        enum "America/Mexico_City" {
                            value "103";
                        }
                        enum "America/Miquelon" {
                            value "104";
                        }
                        enum "America/Moncton" {
                            value "105";
                        }
                        enum "America/Monterrey" {
                            value "106";
                        }
                        enum "America/Montevideo" {
                            value "107";
                        }
                        enum "America/Nassau" {
                            value "108";
                        }
                        enum "America/New_York" {
                            value "109";
                        }
                        enum "America/Nipigon" {
                            value "110";
                        }
                        enum "America/Nome" {
                            value "111";
                        }
                        enum "America/Noronha" {
                            value "112";
                        }
                        enum "America/North_Dakota/Beulah" {
                            value "113";
                        }
                        enum "America/North_Dakota/Center" {
                            value "114";
                        }
                        enum "America/North_Dakota/New_Salem" {
                            value "115";
                        }
                        enum "America/Nuuk" {
                            value "116";
                        }
                        enum "America/Ojinaga" {
                            value "117";
                        }
                        enum "America/Panama" {
                            value "118";
                        }
                        enum "America/Pangnirtung" {
                            value "119";
                        }
                        enum "America/Paramaribo" {
                            value "120";
                        }
                        enum "America/Phoenix" {
                            value "121";
                        }
                        enum "America/Port-au-Prince" {
                            value "122";
                        }
                        enum "America/Port_of_Spain" {
                            value "123";
                        }
                        enum "America/Porto_Velho" {
                            value "124";
                        }
                        enum "America/Puerto_Rico" {
                            value "125";
                        }
                        enum "America/Punta_Arenas" {
                            value "126";
                        }
                        enum "America/Rainy_River" {
                            value "127";
                        }
                        enum "America/Rankin_Inlet" {
                            value "128";
                        }
                        enum "America/Recife" {
                            value "129";
                        }
                        enum "America/Regina" {
                            value "130";
                        }
                        enum "America/Resolute" {
                            value "131";
                        }
                        enum "America/Rio_Branco" {
                            value "132";
                        }
                        enum "America/Santarem" {
                            value "133";
                        }
                        enum "America/Santiago" {
                            value "134";
                        }
                        enum "America/Santo_Domingo" {
                            value "135";
                        }
                        enum "America/Sao_Paulo" {
                            value "136";
                        }
                        enum "America/Scoresbysund" {
                            value "137";
                        }
                        enum "America/Sitka" {
                            value "138";
                        }
                        enum "America/St_Johns" {
                            value "139";
                        }
                        enum "America/Swift_Current" {
                            value "140";
                        }
                        enum "America/Tegucigalpa" {
                            value "141";
                        }
                        enum "America/Thule" {
                            value "142";
                        }
                        enum "America/Thunder_Bay" {
                            value "143";
                        }
                        enum "America/Tijuana" {
                            value "144";
                        }
                        enum "America/Toronto" {
                            value "145";
                        }
                        enum "America/Vancouver" {
                            value "146";
                        }
                        enum "America/Whitehorse" {
                            value "147";
                        }
                        enum "America/Winnipeg" {
                            value "148";
                        }
                        enum "America/Yakutat" {
                            value "149";
                        }
                        enum "America/Yellowknife" {
                            value "150";
                        }
                        enum "Antarctica/Casey" {
                            value "151";
                        }
                        enum "Antarctica/Davis" {
                            value "152";
                        }
                        enum "Antarctica/DumontDUrville" {
                            value "153";
                        }
                        enum "Antarctica/Macquarie" {
                            value "154";
                        }
                        enum "Antarctica/Mawson" {
                            value "155";
                        }
                        enum "Antarctica/Palmer" {
                            value "156";
                        }
                        enum "Antarctica/Rothera" {
                            value "157";
                        }
                        enum "Antarctica/Syowa" {
                            value "158";
                        }
                        enum "Antarctica/Troll" {
                            value "159";
                        }
                        enum "Antarctica/Vostok" {
                            value "160";
                        }
                        enum "Asia/Almaty" {
                            value "161";
                        }
                        enum "Asia/Amman" {
                            value "162";
                        }
                        enum "Asia/Anadyr" {
                            value "163";
                        }
                        enum "Asia/Aqtau" {
                            value "164";
                        }
                        enum "Asia/Aqtobe" {
                            value "165";
                        }
                        enum "Asia/Ashgabat" {
                            value "166";
                        }
                        enum "Asia/Atyrau" {
                            value "167";
                        }
                        enum "Asia/Baghdad" {
                            value "168";
                        }
                        enum "Asia/Baku" {
                            value "169";
                        }
                        enum "Asia/Bangkok" {
                            value "170";
                        }
                        enum "Asia/Barnaul" {
                            value "171";
                        }
                        enum "Asia/Beirut" {
                            value "172";
                        }
                        enum "Asia/Bishkek" {
                            value "173";
                        }
                        enum "Asia/Brunei" {
                            value "174";
                        }
                        enum "Asia/Chita" {
                            value "175";
                        }
                        enum "Asia/Choibalsan" {
                            value "176";
                        }
                        enum "Asia/Colombo" {
                            value "177";
                        }
                        enum "Asia/Damascus" {
                            value "178";
                        }
                        enum "Asia/Dhaka" {
                            value "179";
                        }
                        enum "Asia/Dili" {
                            value "180";
                        }
                        enum "Asia/Dubai" {
                            value "181";
                        }
                        enum "Asia/Dushanbe" {
                            value "182";
                        }
                        enum "Asia/Famagusta" {
                            value "183";
                        }
                        enum "Asia/Gaza" {
                            value "184";
                        }
                        enum "Asia/Hebron" {
                            value "185";
                        }
                        enum "Asia/Ho_Chi_Minh" {
                            value "186";
                        }
                        enum "Asia/Hong_Kong" {
                            value "187";
                        }
                        enum "Asia/Hovd" {
                            value "188";
                        }
                        enum "Asia/Irkutsk" {
                            value "189";
                        }
                        enum "Asia/Jakarta" {
                            value "190";
                        }
                        enum "Asia/Jayapura" {
                            value "191";
                        }
                        enum "Asia/Jerusalem" {
                            value "192";
                        }
                        enum "Asia/Kabul" {
                            value "193";
                        }
                        enum "Asia/Kamchatka" {
                            value "194";
                        }
                        enum "Asia/Karachi" {
                            value "195";
                        }
                        enum "Asia/Kathmandu" {
                            value "196";
                        }
                        enum "Asia/Khandyga" {
                            value "197";
                        }
                        enum "Asia/Kolkata" {
                            value "198";
                        }
                        enum "Asia/Krasnoyarsk" {
                            value "199";
                        }
                        enum "Asia/Kuala_Lumpur" {
                            value "200";
                        }
                        enum "Asia/Kuching" {
                            value "201";
                        }
                        enum "Asia/Macau" {
                            value "202";
                        }
                        enum "Asia/Magadan" {
                            value "203";
                        }
                        enum "Asia/Makassar" {
                            value "204";
                        }
                        enum "Asia/Manila" {
                            value "205";
                        }
                        enum "Asia/Nicosia" {
                            value "206";
                        }
                        enum "Asia/Novokuznetsk" {
                            value "207";
                        }
                        enum "Asia/Novosibirsk" {
                            value "208";
                        }
                        enum "Asia/Omsk" {
                            value "209";
                        }
                        enum "Asia/Oral" {
                            value "210";
                        }
                        enum "Asia/Pontianak" {
                            value "211";
                        }
                        enum "Asia/Pyongyang" {
                            value "212";
                        }
                        enum "Asia/Qatar" {
                            value "213";
                        }
                        enum "Asia/Qostanay" {
                            value "214";
                        }
                        enum "Asia/Qyzylorda" {
                            value "215";
                        }
                        enum "Asia/Riyadh" {
                            value "216";
                        }
                        enum "Asia/Sakhalin" {
                            value "217";
                        }
                        enum "Asia/Samarkand" {
                            value "218";
                        }
                        enum "Asia/Seoul" {
                            value "219";
                        }
                        enum "Asia/Shanghai" {
                            value "220";
                        }
                        enum "Asia/Singapore" {
                            value "221";
                        }
                        enum "Asia/Srednekolymsk" {
                            value "222";
                        }
                        enum "Asia/Taipei" {
                            value "223";
                        }
                        enum "Asia/Tashkent" {
                            value "224";
                        }
                        enum "Asia/Tbilisi" {
                            value "225";
                        }
                        enum "Asia/Tehran" {
                            value "226";
                        }
                        enum "Asia/Thimphu" {
                            value "227";
                        }
                        enum "Asia/Tokyo" {
                            value "228";
                        }
                        enum "Asia/Tomsk" {
                            value "229";
                        }
                        enum "Asia/Ulaanbaatar" {
                            value "230";
                        }
                        enum "Asia/Urumqi" {
                            value "231";
                        }
                        enum "Asia/Ust-Nera" {
                            value "232";
                        }
                        enum "Asia/Vladivostok" {
                            value "233";
                        }
                        enum "Asia/Yakutsk" {
                            value "234";
                        }
                        enum "Asia/Yangon" {
                            value "235";
                        }
                        enum "Asia/Yekaterinburg" {
                            value "236";
                        }
                        enum "Asia/Yerevan" {
                            value "237";
                        }
                        enum "Atlantic/Azores" {
                            value "238";
                        }
                        enum "Atlantic/Bermuda" {
                            value "239";
                        }
                        enum "Atlantic/Canary" {
                            value "240";
                        }
                        enum "Atlantic/Cape_Verde" {
                            value "241";
                        }
                        enum "Atlantic/Faroe" {
                            value "242";
                        }
                        enum "Atlantic/Madeira" {
                            value "243";
                        }
                        enum "Atlantic/Reykjavik" {
                            value "244";
                        }
                        enum "Atlantic/South_Georgia" {
                            value "245";
                        }
                        enum "Atlantic/Stanley" {
                            value "246";
                        }
                        enum "Australia/Adelaide" {
                            value "247";
                        }
                        enum "Australia/Brisbane" {
                            value "248";
                        }
                        enum "Australia/Broken_Hill" {
                            value "249";
                        }
                        enum "Australia/Currie" {
                            value "250";
                        }
                        enum "Australia/Darwin" {
                            value "251";
                        }
                        enum "Australia/Eucla" {
                            value "252";
                        }
                        enum "Australia/Hobart" {
                            value "253";
                        }
                        enum "Australia/Lindeman" {
                            value "254";
                        }
                        enum "Australia/Lord_Howe" {
                            value "255";
                        }
                        enum "Australia/Melbourne" {
                            value "256";
                        }
                        enum "Australia/Perth" {
                            value "257";
                        }
                        enum "Australia/Sydney" {
                            value "258";
                        }
                        enum "Europe/Amsterdam" {
                            value "259";
                        }
                        enum "Europe/Andorra" {
                            value "260";
                        }
                        enum "Europe/Astrakhan" {
                            value "261";
                        }
                        enum "Europe/Athens" {
                            value "262";
                        }
                        enum "Europe/Belgrade" {
                            value "263";
                        }
                        enum "Europe/Berlin" {
                            value "264";
                        }
                        enum "Europe/Brussels" {
                            value "265";
                        }
                        enum "Europe/Bucharest" {
                            value "266";
                        }
                        enum "Europe/Budapest" {
                            value "267";
                        }
                        enum "Europe/Chisinau" {
                            value "268";
                        }
                        enum "Europe/Copenhagen" {
                            value "269";
                        }
                        enum "Europe/Dublin" {
                            value "270";
                        }
                        enum "Europe/Gibraltar" {
                            value "271";
                        }
                        enum "Europe/Helsinki" {
                            value "272";
                        }
                        enum "Europe/Istanbul" {
                            value "273";
                        }
                        enum "Europe/Kaliningrad" {
                            value "274";
                        }
                        enum "Europe/Kiev" {
                            value "275";
                        }
                        enum "Europe/Kirov" {
                            value "276";
                        }
                        enum "Europe/Lisbon" {
                            value "277";
                        }
                        enum "Europe/London" {
                            value "278";
                        }
                        enum "Europe/Luxembourg" {
                            value "279";
                        }
                        enum "Europe/Madrid" {
                            value "280";
                        }
                        enum "Europe/Malta" {
                            value "281";
                        }
                        enum "Europe/Minsk" {
                            value "282";
                        }
                        enum "Europe/Monaco" {
                            value "283";
                        }
                        enum "Europe/Moscow" {
                            value "284";
                        }
                        enum "Europe/Oslo" {
                            value "285";
                        }
                        enum "Europe/Paris" {
                            value "286";
                        }
                        enum "Europe/Prague" {
                            value "287";
                        }
                        enum "Europe/Riga" {
                            value "288";
                        }
                        enum "Europe/Rome" {
                            value "289";
                        }
                        enum "Europe/Samara" {
                            value "290";
                        }
                        enum "Europe/Saratov" {
                            value "291";
                        }
                        enum "Europe/Simferopol" {
                            value "292";
                        }
                        enum "Europe/Sofia" {
                            value "293";
                        }
                        enum "Europe/Stockholm" {
                            value "294";
                        }
                        enum "Europe/Tallinn" {
                            value "295";
                        }
                        enum "Europe/Tirane" {
                            value "296";
                        }
                        enum "Europe/Ulyanovsk" {
                            value "297";
                        }
                        enum "Europe/Uzhgorod" {
                            value "298";
                        }
                        enum "Europe/Vienna" {
                            value "299";
                        }
                        enum "Europe/Vilnius" {
                            value "300";
                        }
                        enum "Europe/Volgograd" {
                            value "301";
                        }
                        enum "Europe/Warsaw" {
                            value "302";
                        }
                        enum "Europe/Zaporozhye" {
                            value "303";
                        }
                        enum "Europe/Zurich" {
                            value "304";
                        }
                        enum "Indian/Chagos" {
                            value "305";
                        }
                        enum "Indian/Christmas" {
                            value "306";
                        }
                        enum "Indian/Cocos" {
                            value "307";
                        }
                        enum "Indian/Kerguelen" {
                            value "308";
                        }
                        enum "Indian/Mahe" {
                            value "309";
                        }
                        enum "Indian/Maldives" {
                            value "310";
                        }
                        enum "Indian/Mauritius" {
                            value "311";
                        }
                        enum "Indian/Reunion" {
                            value "312";
                        }
                        enum "Pacific/Apia" {
                            value "313";
                        }
                        enum "Pacific/Auckland" {
                            value "314";
                        }
                        enum "Pacific/Bougainville" {
                            value "315";
                        }
                        enum "Pacific/Chatham" {
                            value "316";
                        }
                        enum "Pacific/Chuuk" {
                            value "317";
                        }
                        enum "Pacific/Easter" {
                            value "318";
                        }
                        enum "Pacific/Efate" {
                            value "319";
                        }
                        enum "Pacific/Enderbury" {
                            value "320";
                        }
                        enum "Pacific/Fakaofo" {
                            value "321";
                        }
                        enum "Pacific/Fiji" {
                            value "322";
                        }
                        enum "Pacific/Funafuti" {
                            value "323";
                        }
                        enum "Pacific/Galapagos" {
                            value "324";
                        }
                        enum "Pacific/Gambier" {
                            value "325";
                        }
                        enum "Pacific/Guadalcanal" {
                            value "326";
                        }
                        enum "Pacific/Guam" {
                            value "327";
                        }
                        enum "Pacific/Honolulu" {
                            value "328";
                        }
                        enum "Pacific/Kiritimati" {
                            value "329";
                        }
                        enum "Pacific/Kosrae" {
                            value "330";
                        }
                        enum "Pacific/Kwajalein" {
                            value "331";
                        }
                        enum "Pacific/Majuro" {
                            value "332";
                        }
                        enum "Pacific/Marquesas" {
                            value "333";
                        }
                        enum "Pacific/Nauru" {
                            value "334";
                        }
                        enum "Pacific/Niue" {
                            value "335";
                        }
                        enum "Pacific/Norfolk" {
                            value "336";
                        }
                        enum "Pacific/Noumea" {
                            value "337";
                        }
                        enum "Pacific/Pago_Pago" {
                            value "338";
                        }
                        enum "Pacific/Palau" {
                            value "339";
                        }
                        enum "Pacific/Pitcairn" {
                            value "340";
                        }
                        enum "Pacific/Pohnpei" {
                            value "341";
                        }
                        enum "Pacific/Port_Moresby" {
                            value "342";
                        }
                        enum "Pacific/Rarotonga" {
                            value "343";
                        }
                        enum "Pacific/Tahiti" {
                            value "344";
                        }
                        enum "Pacific/Tarawa" {
                            value "345";
                        }
                        enum "Pacific/Tongatapu" {
                            value "346";
                        }
                        enum "Pacific/Wake" {
                            value "347";
                        }
                        enum "Pacific/Wallis" {
                            value "348";
                        }
                    }
                }
                leaf "RR_Time_GnssPpsOffset" {
                    when "not ((/config_data/device/DeviceHw/RR_DynHw_Module_Gps = 'Off') or (/config_data/main/Gnss/RR_Gnss_Enable = 'Off') or (/config_data/main/Time/RR_Time_GnssSynchEn = 'Off'))";
                    type "uint16" {
                        range "0..999";
                    }
                }
                leaf "RR_Time_GnssMinJitter" {
                    when "not ((/config_data/device/DeviceHw/RR_DynHw_Module_Gps = 'Off') or (/config_data/main/Gnss/RR_Gnss_Enable = 'Off') or (/config_data/main/Time/RR_Time_GnssSynchEn = 'Off'))";
                    type "uint16" {
                        range "0..999";
                    }
                }
            }
            container "FW" {
                leaf "RR_FW_DowngradeEnable" {
                    type "lbox_off_on";
                }
            }
            container "FwDistribution" {
                when "not (/config_data/device/DeviceHw/RR_DynHw_FwDistribution != 'On')";
                leaf "RR_FwDist_SenderEn" {
                    type "lbox_off_on";
                }
                leaf "RR_FwDist_ReceiverEn" {
                    type "lbox_off_on";
                }
            }
            container "FwDistCommon" {
                when "not ((/config_data/device/DeviceHw/RR_DynHw_FwDistribution != 'On') or ((/config_data/main/FwDistribution/RR_FwDist_SenderEn != 'On') and (/config_data/main/FwDistribution/RR_FwDist_ReceiverEn != 'On')))";
                leaf "RR_FwDist_PublicMcastAddr" {
                    type "inet:ipv4-address";
                }
                leaf "RR_FwDist_KeySource" {
                    type "lbox_default_user";
                }
                leaf "RR_FwDist_DSCP" {
                    type "lim_qos_dscp";
                }
                leaf "RR_FwDist_KeyId" {
                    when "not (/config_data/main/FwDistCommon/RR_FwDist_KeySource != 'LB_default_user_User')";
                    type "string" {
                        pattern "[a-zA-Z0-9_]{0,128}";
                    }
                }
            }
            container "FwDistSender" {
                when "not ((/config_data/device/DeviceHw/RR_DynHw_FwDistribution != 'On') or (/config_data/main/FwDistribution/RR_FwDist_SenderEn != 'On'))";
                leaf "RR_FwDistSnd_PrivateMcastAddr" {
                    type "inet:ipv4-address";
                }
            }
            container "Gnss" {
                leaf "RR_Gnss_Enable" {
                    when "not (/config_data/device/DeviceHw/RR_DynHw_Module_Gps = 'Off')";
                    type "lbox_off_on";
                }
                leaf "RR_Gnss_ServerEnable" {
                    when "not ((/config_data/device/DeviceHw/RR_DynHw_Module_Gps = 'Off') or (/config_data/main/Gnss/RR_Gnss_Enable = 'Off'))";
                    type "lbox_off_on";
                }
                leaf "RR_Gnss_ServerPort" {
                    when "not ((/config_data/device/DeviceHw/RR_DynHw_Module_Gps = 'Off') or (/config_data/main/Gnss/RR_Gnss_Enable = 'Off') or (/config_data/main/Gnss/RR_Gnss_ServerEnable = 'Off'))";
                    type "lim_udp_port";
                }
                leaf "RR_Gnss_MaxDowntime" {
                    when "not ((/config_data/device/DeviceHw/RR_DynHw_Module_Gps = 'Off') or (/config_data/main/Gnss/RR_Gnss_Enable = 'Off'))";
                    type "lim_uint_16_1toFF";
                }
            }
            container "KrngGenCrtKey" {
                leaf "RR_KrngGCKey_Algorithm" {
                    type "enumeration" {
                        enum "RSA" {
                            value "0";
                        }
                        enum "EC" {
                            value "1";
                        }
                        enum "ED25519" {
                            value "2";
                        }
                        enum "ED448" {
                            value "3";
                        }
                    }
                }
                leaf "RR_KrngGCKey_RsaLength" {
                    when "not (/config_data/main/KrngGenCrtKey/RR_KrngGCKey_Algorithm != 'RSA')";
                    type "enumeration" {
                        enum "2048" {
                            value "0";
                        }
                        enum "3072" {
                            value "1";
                        }
                        enum "4096" {
                            value "2";
                        }
                    }
                }
                leaf "RR_KrngGCKey_EcCurve" {
                    when "not (/config_data/main/KrngGenCrtKey/RR_KrngGCKey_Algorithm != 'EC')";
                    type "enumeration" {
                        enum "P-224 (secp224r1)" {
                            value "0";
                        }
                        enum "P-256 (prime256v1)" {
                            value "1";
                        }
                        enum "P-384 (secp384r1)" {
                            value "2";
                        }
                        enum "P-521 (secp521r1)" {
                            value "3";
                        }
                    }
                }
            }
            container "KrngGenCert" {
                leaf "RR_KrngGCrt_SignDigestAlg" {
                    type "enumeration" {
                        enum "SHA256" {
                            value "0";
                        }
                        enum "SHA384" {
                            value "1";
                        }
                        enum "SHA512" {
                            value "2";
                        }
                    }
                }
                leaf "RR_KrngGCrt_Country" {
                    type "enumeration" {
                        enum "LB_KrngGCrt_Country_AD" {
                            value "1";
                        }
                        enum "LB_KrngGCrt_Country_AE" {
                            value "2";
                        }
                        enum "LB_KrngGCrt_Country_AF" {
                            value "3";
                        }
                        enum "LB_KrngGCrt_Country_AG" {
                            value "4";
                        }
                        enum "LB_KrngGCrt_Country_AI" {
                            value "5";
                        }
                        enum "LB_KrngGCrt_Country_AL" {
                            value "6";
                        }
                        enum "LB_KrngGCrt_Country_AM" {
                            value "7";
                        }
                        enum "LB_KrngGCrt_Country_AO" {
                            value "8";
                        }
                        enum "LB_KrngGCrt_Country_AQ" {
                            value "9";
                        }
                        enum "LB_KrngGCrt_Country_AR" {
                            value "10";
                        }
                        enum "LB_KrngGCrt_Country_AS" {
                            value "11";
                        }
                        enum "LB_KrngGCrt_Country_AT" {
                            value "12";
                        }
                        enum "LB_KrngGCrt_Country_AU" {
                            value "13";
                        }
                        enum "LB_KrngGCrt_Country_AW" {
                            value "14";
                        }
                        enum "LB_KrngGCrt_Country_AX" {
                            value "15";
                        }
                        enum "LB_KrngGCrt_Country_AZ" {
                            value "16";
                        }
                        enum "LB_KrngGCrt_Country_BA" {
                            value "17";
                        }
                        enum "LB_KrngGCrt_Country_BB" {
                            value "18";
                        }
                        enum "LB_KrngGCrt_Country_BD" {
                            value "19";
                        }
                        enum "LB_KrngGCrt_Country_BE" {
                            value "20";
                        }
                        enum "LB_KrngGCrt_Country_BF" {
                            value "21";
                        }
                        enum "LB_KrngGCrt_Country_BG" {
                            value "22";
                        }
                        enum "LB_KrngGCrt_Country_BH" {
                            value "23";
                        }
                        enum "LB_KrngGCrt_Country_BI" {
                            value "24";
                        }
                        enum "LB_KrngGCrt_Country_BJ" {
                            value "25";
                        }
                        enum "LB_KrngGCrt_Country_BL" {
                            value "26";
                        }
                        enum "LB_KrngGCrt_Country_BM" {
                            value "27";
                        }
                        enum "LB_KrngGCrt_Country_BN" {
                            value "28";
                        }
                        enum "LB_KrngGCrt_Country_BO" {
                            value "29";
                        }
                        enum "LB_KrngGCrt_Country_BQ" {
                            value "30";
                        }
                        enum "LB_KrngGCrt_Country_BR" {
                            value "31";
                        }
                        enum "LB_KrngGCrt_Country_BS" {
                            value "32";
                        }
                        enum "LB_KrngGCrt_Country_BT" {
                            value "33";
                        }
                        enum "LB_KrngGCrt_Country_BV" {
                            value "34";
                        }
                        enum "LB_KrngGCrt_Country_BW" {
                            value "35";
                        }
                        enum "LB_KrngGCrt_Country_BZ" {
                            value "36";
                        }
                        enum "LB_KrngGCrt_Country_CA" {
                            value "37";
                        }
                        enum "LB_KrngGCrt_Country_CC" {
                            value "38";
                        }
                        enum "LB_KrngGCrt_Country_CD" {
                            value "39";
                        }
                        enum "LB_KrngGCrt_Country_CF" {
                            value "40";
                        }
                        enum "LB_KrngGCrt_Country_CG" {
                            value "41";
                        }
                        enum "LB_KrngGCrt_Country_CH" {
                            value "42";
                        }
                        enum "LB_KrngGCrt_Country_CK" {
                            value "43";
                        }
                        enum "LB_KrngGCrt_Country_CL" {
                            value "44";
                        }
                        enum "LB_KrngGCrt_Country_CM" {
                            value "45";
                        }
                        enum "LB_KrngGCrt_Country_CN" {
                            value "46";
                        }
                        enum "LB_KrngGCrt_Country_CO" {
                            value "47";
                        }
                        enum "LB_KrngGCrt_Country_CR" {
                            value "48";
                        }
                        enum "LB_KrngGCrt_Country_CV" {
                            value "49";
                        }
                        enum "LB_KrngGCrt_Country_CW" {
                            value "50";
                        }
                        enum "LB_KrngGCrt_Country_CX" {
                            value "51";
                        }
                        enum "LB_KrngGCrt_Country_CY" {
                            value "52";
                        }
                        enum "LB_KrngGCrt_Country_CZ" {
                            value "53";
                        }
                        enum "LB_KrngGCrt_Country_DE" {
                            value "54";
                        }
                        enum "LB_KrngGCrt_Country_DJ" {
                            value "55";
                        }
                        enum "LB_KrngGCrt_Country_DK" {
                            value "56";
                        }
                        enum "LB_KrngGCrt_Country_DM" {
                            value "57";
                        }
                        enum "LB_KrngGCrt_Country_DO" {
                            value "58";
                        }
                        enum "LB_KrngGCrt_Country_DZ" {
                            value "59";
                        }
                        enum "LB_KrngGCrt_Country_EC" {
                            value "60";
                        }
                        enum "LB_KrngGCrt_Country_EE" {
                            value "61";
                        }
                        enum "LB_KrngGCrt_Country_EG" {
                            value "62";
                        }
                        enum "LB_KrngGCrt_Country_EH" {
                            value "63";
                        }
                        enum "LB_KrngGCrt_Country_ER" {
                            value "64";
                        }
                        enum "LB_KrngGCrt_Country_ES" {
                            value "65";
                        }
                        enum "LB_KrngGCrt_Country_ET" {
                            value "66";
                        }
                        enum "LB_KrngGCrt_Country_FI" {
                            value "67";
                        }
                        enum "LB_KrngGCrt_Country_FJ" {
                            value "68";
                        }
                        enum "LB_KrngGCrt_Country_FK" {
                            value "69";
                        }
                        enum "LB_KrngGCrt_Country_FM" {
                            value "70";
                        }
                        enum "LB_KrngGCrt_Country_FO" {
                            value "71";
                        }
                        enum "LB_KrngGCrt_Country_FR" {
                            value "72";
                        }
                        enum "LB_KrngGCrt_Country_GA" {
                            value "73";
                        }
                        enum "LB_KrngGCrt_Country_GB" {
                            value "74";
                        }
                        enum "LB_KrngGCrt_Country_GD" {
                            value "75";
                        }
                        enum "LB_KrngGCrt_Country_GE" {
                            value "76";
                        }
                        enum "LB_KrngGCrt_Country_GF" {
                            value "77";
                        }
                        enum "LB_KrngGCrt_Country_GG" {
                            value "78";
                        }
                        enum "LB_KrngGCrt_Country_GH" {
                            value "79";
                        }
                        enum "LB_KrngGCrt_Country_GI" {
                            value "80";
                        }
                        enum "LB_KrngGCrt_Country_GL" {
                            value "81";
                        }
                        enum "LB_KrngGCrt_Country_GM" {
                            value "82";
                        }
                        enum "LB_KrngGCrt_Country_GN" {
                            value "83";
                        }
                        enum "LB_KrngGCrt_Country_GP" {
                            value "84";
                        }
                        enum "LB_KrngGCrt_Country_GQ" {
                            value "85";
                        }
                        enum "LB_KrngGCrt_Country_GR" {
                            value "86";
                        }
                        enum "LB_KrngGCrt_Country_GS" {
                            value "87";
                        }
                        enum "LB_KrngGCrt_Country_GT" {
                            value "88";
                        }
                        enum "LB_KrngGCrt_Country_GU" {
                            value "89";
                        }
                        enum "LB_KrngGCrt_Country_GW" {
                            value "90";
                        }
                        enum "LB_KrngGCrt_Country_GY" {
                            value "91";
                        }
                        enum "LB_KrngGCrt_Country_HK" {
                            value "92";
                        }
                        enum "LB_KrngGCrt_Country_HM" {
                            value "93";
                        }
                        enum "LB_KrngGCrt_Country_HN" {
                            value "94";
                        }
                        enum "LB_KrngGCrt_Country_HR" {
                            value "95";
                        }
                        enum "LB_KrngGCrt_Country_HT" {
                            value "96";
                        }
                        enum "LB_KrngGCrt_Country_HU" {
                            value "97";
                        }
                        enum "LB_KrngGCrt_Country_ID" {
                            value "98";
                        }
                        enum "LB_KrngGCrt_Country_IE" {
                            value "99";
                        }
                        enum "LB_KrngGCrt_Country_IL" {
                            value "100";
                        }
                        enum "LB_KrngGCrt_Country_IM" {
                            value "101";
                        }
                        enum "LB_KrngGCrt_Country_IN" {
                            value "102";
                        }
                        enum "LB_KrngGCrt_Country_IO" {
                            value "103";
                        }
                        enum "LB_KrngGCrt_Country_IQ" {
                            value "104";
                        }
                        enum "LB_KrngGCrt_Country_IS" {
                            value "105";
                        }
                        enum "LB_KrngGCrt_Country_IT" {
                            value "106";
                        }
                        enum "LB_KrngGCrt_Country_JE" {
                            value "107";
                        }
                        enum "LB_KrngGCrt_Country_JM" {
                            value "108";
                        }
                        enum "LB_KrngGCrt_Country_JO" {
                            value "109";
                        }
                        enum "LB_KrngGCrt_Country_JP" {
                            value "110";
                        }
                        enum "LB_KrngGCrt_Country_KE" {
                            value "111";
                        }
                        enum "LB_KrngGCrt_Country_KG" {
                            value "112";
                        }
                        enum "LB_KrngGCrt_Country_KH" {
                            value "113";
                        }
                        enum "LB_KrngGCrt_Country_KI" {
                            value "114";
                        }
                        enum "LB_KrngGCrt_Country_KM" {
                            value "115";
                        }
                        enum "LB_KrngGCrt_Country_KN" {
                            value "116";
                        }
                        enum "LB_KrngGCrt_Country_KR" {
                            value "117";
                        }
                        enum "LB_KrngGCrt_Country_KW" {
                            value "118";
                        }
                        enum "LB_KrngGCrt_Country_KY" {
                            value "119";
                        }
                        enum "LB_KrngGCrt_Country_KZ" {
                            value "120";
                        }
                        enum "LB_KrngGCrt_Country_LA" {
                            value "121";
                        }
                        enum "LB_KrngGCrt_Country_LB" {
                            value "122";
                        }
                        enum "LB_KrngGCrt_Country_LC" {
                            value "123";
                        }
                        enum "LB_KrngGCrt_Country_LI" {
                            value "124";
                        }
                        enum "LB_KrngGCrt_Country_LK" {
                            value "125";
                        }
                        enum "LB_KrngGCrt_Country_LR" {
                            value "126";
                        }
                        enum "LB_KrngGCrt_Country_LS" {
                            value "127";
                        }
                        enum "LB_KrngGCrt_Country_LT" {
                            value "128";
                        }
                        enum "LB_KrngGCrt_Country_LU" {
                            value "129";
                        }
                        enum "LB_KrngGCrt_Country_LV" {
                            value "130";
                        }
                        enum "LB_KrngGCrt_Country_LY" {
                            value "131";
                        }
                        enum "LB_KrngGCrt_Country_MA" {
                            value "132";
                        }
                        enum "LB_KrngGCrt_Country_MC" {
                            value "133";
                        }
                        enum "LB_KrngGCrt_Country_MD" {
                            value "134";
                        }
                        enum "LB_KrngGCrt_Country_ME" {
                            value "135";
                        }
                        enum "LB_KrngGCrt_Country_MF" {
                            value "136";
                        }
                        enum "LB_KrngGCrt_Country_MG" {
                            value "137";
                        }
                        enum "LB_KrngGCrt_Country_MH" {
                            value "138";
                        }
                        enum "LB_KrngGCrt_Country_MK" {
                            value "139";
                        }
                        enum "LB_KrngGCrt_Country_ML" {
                            value "140";
                        }
                        enum "LB_KrngGCrt_Country_MM" {
                            value "141";
                        }
                        enum "LB_KrngGCrt_Country_MN" {
                            value "142";
                        }
                        enum "LB_KrngGCrt_Country_MO" {
                            value "143";
                        }
                        enum "LB_KrngGCrt_Country_MP" {
                            value "144";
                        }
                        enum "LB_KrngGCrt_Country_MQ" {
                            value "145";
                        }
                        enum "LB_KrngGCrt_Country_MR" {
                            value "146";
                        }
                        enum "LB_KrngGCrt_Country_MS" {
                            value "147";
                        }
                        enum "LB_KrngGCrt_Country_MT" {
                            value "148";
                        }
                        enum "LB_KrngGCrt_Country_MU" {
                            value "149";
                        }
                        enum "LB_KrngGCrt_Country_MV" {
                            value "150";
                        }
                        enum "LB_KrngGCrt_Country_MW" {
                            value "151";
                        }
                        enum "LB_KrngGCrt_Country_MX" {
                            value "152";
                        }
                        enum "LB_KrngGCrt_Country_MY" {
                            value "153";
                        }
                        enum "LB_KrngGCrt_Country_MZ" {
                            value "154";
                        }
                        enum "LB_KrngGCrt_Country_NA" {
                            value "155";
                        }
                        enum "LB_KrngGCrt_Country_NC" {
                            value "156";
                        }
                        enum "LB_KrngGCrt_Country_NE" {
                            value "157";
                        }
                        enum "LB_KrngGCrt_Country_NF" {
                            value "158";
                        }
                        enum "LB_KrngGCrt_Country_NG" {
                            value "159";
                        }
                        enum "LB_KrngGCrt_Country_NI" {
                            value "160";
                        }
                        enum "LB_KrngGCrt_Country_NL" {
                            value "161";
                        }
                        enum "LB_KrngGCrt_Country_NO" {
                            value "162";
                        }
                        enum "LB_KrngGCrt_Country_NP" {
                            value "163";
                        }
                        enum "LB_KrngGCrt_Country_NR" {
                            value "164";
                        }
                        enum "LB_KrngGCrt_Country_NU" {
                            value "165";
                        }
                        enum "LB_KrngGCrt_Country_NZ" {
                            value "166";
                        }
                        enum "LB_KrngGCrt_Country_OM" {
                            value "167";
                        }
                        enum "LB_KrngGCrt_Country_PA" {
                            value "168";
                        }
                        enum "LB_KrngGCrt_Country_PE" {
                            value "169";
                        }
                        enum "LB_KrngGCrt_Country_PF" {
                            value "170";
                        }
                        enum "LB_KrngGCrt_Country_PG" {
                            value "171";
                        }
                        enum "LB_KrngGCrt_Country_PH" {
                            value "172";
                        }
                        enum "LB_KrngGCrt_Country_PK" {
                            value "173";
                        }
                        enum "LB_KrngGCrt_Country_PL" {
                            value "174";
                        }
                        enum "LB_KrngGCrt_Country_PM" {
                            value "175";
                        }
                        enum "LB_KrngGCrt_Country_PN" {
                            value "176";
                        }
                        enum "LB_KrngGCrt_Country_PR" {
                            value "177";
                        }
                        enum "LB_KrngGCrt_Country_PS" {
                            value "178";
                        }
                        enum "LB_KrngGCrt_Country_PT" {
                            value "179";
                        }
                        enum "LB_KrngGCrt_Country_PW" {
                            value "180";
                        }
                        enum "LB_KrngGCrt_Country_PY" {
                            value "181";
                        }
                        enum "LB_KrngGCrt_Country_QA" {
                            value "182";
                        }
                        enum "LB_KrngGCrt_Country_RE" {
                            value "183";
                        }
                        enum "LB_KrngGCrt_Country_RO" {
                            value "184";
                        }
                        enum "LB_KrngGCrt_Country_RS" {
                            value "185";
                        }
                        enum "LB_KrngGCrt_Country_RW" {
                            value "186";
                        }
                        enum "LB_KrngGCrt_Country_SA" {
                            value "187";
                        }
                        enum "LB_KrngGCrt_Country_SB" {
                            value "188";
                        }
                        enum "LB_KrngGCrt_Country_SC" {
                            value "189";
                        }
                        enum "LB_KrngGCrt_Country_SE" {
                            value "190";
                        }
                        enum "LB_KrngGCrt_Country_SG" {
                            value "191";
                        }
                        enum "LB_KrngGCrt_Country_SH" {
                            value "192";
                        }
                        enum "LB_KrngGCrt_Country_SI" {
                            value "193";
                        }
                        enum "LB_KrngGCrt_Country_SJ" {
                            value "194";
                        }
                        enum "LB_KrngGCrt_Country_SK" {
                            value "195";
                        }
                        enum "LB_KrngGCrt_Country_SL" {
                            value "196";
                        }
                        enum "LB_KrngGCrt_Country_SM" {
                            value "197";
                        }
                        enum "LB_KrngGCrt_Country_SN" {
                            value "198";
                        }
                        enum "LB_KrngGCrt_Country_SO" {
                            value "199";
                        }
                        enum "LB_KrngGCrt_Country_SR" {
                            value "200";
                        }
                        enum "LB_KrngGCrt_Country_SS" {
                            value "201";
                        }
                        enum "LB_KrngGCrt_Country_ST" {
                            value "202";
                        }
                        enum "LB_KrngGCrt_Country_SV" {
                            value "203";
                        }
                        enum "LB_KrngGCrt_Country_SX" {
                            value "204";
                        }
                        enum "LB_KrngGCrt_Country_TC" {
                            value "205";
                        }
                        enum "LB_KrngGCrt_Country_TD" {
                            value "206";
                        }
                        enum "LB_KrngGCrt_Country_TF" {
                            value "207";
                        }
                        enum "LB_KrngGCrt_Country_TG" {
                            value "208";
                        }
                        enum "LB_KrngGCrt_Country_TH" {
                            value "209";
                        }
                        enum "LB_KrngGCrt_Country_TJ" {
                            value "210";
                        }
                        enum "LB_KrngGCrt_Country_TK" {
                            value "211";
                        }
                        enum "LB_KrngGCrt_Country_TM" {
                            value "212";
                        }
                        enum "LB_KrngGCrt_Country_TN" {
                            value "213";
                        }
                        enum "LB_KrngGCrt_Country_TO" {
                            value "214";
                        }
                        enum "LB_KrngGCrt_Country_TR" {
                            value "215";
                        }
                        enum "LB_KrngGCrt_Country_TT" {
                            value "216";
                        }
                        enum "LB_KrngGCrt_Country_TV" {
                            value "217";
                        }
                        enum "LB_KrngGCrt_Country_TW" {
                            value "218";
                        }
                        enum "LB_KrngGCrt_Country_TZ" {
                            value "219";
                        }
                        enum "LB_KrngGCrt_Country_UA" {
                            value "220";
                        }
                        enum "LB_KrngGCrt_Country_UG" {
                            value "221";
                        }
                        enum "LB_KrngGCrt_Country_UM" {
                            value "222";
                        }
                        enum "LB_KrngGCrt_Country_US" {
                            value "223";
                        }
                        enum "LB_KrngGCrt_Country_UY" {
                            value "224";
                        }
                        enum "LB_KrngGCrt_Country_UZ" {
                            value "225";
                        }
                        enum "LB_KrngGCrt_Country_VA" {
                            value "226";
                        }
                        enum "LB_KrngGCrt_Country_VC" {
                            value "227";
                        }
                        enum "LB_KrngGCrt_Country_VE" {
                            value "228";
                        }
                        enum "LB_KrngGCrt_Country_VG" {
                            value "229";
                        }
                        enum "LB_KrngGCrt_Country_VI" {
                            value "230";
                        }
                        enum "LB_KrngGCrt_Country_VN" {
                            value "231";
                        }
                        enum "LB_KrngGCrt_Country_VU" {
                            value "232";
                        }
                        enum "LB_KrngGCrt_Country_WF" {
                            value "233";
                        }
                        enum "LB_KrngGCrt_Country_WS" {
                            value "234";
                        }
                        enum "LB_KrngGCrt_Country_YE" {
                            value "235";
                        }
                        enum "LB_KrngGCrt_Country_YT" {
                            value "236";
                        }
                        enum "LB_KrngGCrt_Country_ZA" {
                            value "237";
                        }
                        enum "LB_KrngGCrt_Country_ZM" {
                            value "238";
                        }
                        enum "LB_KrngGCrt_Country_ZW" {
                            value "239";
                        }
                        enum "LB_KrngGCrt_Country_Other" {
                            value "0";
                        }
                    }
                }
                leaf "RR_KrngGCrt_Organization" {
                    type "string" {
                        pattern "[^\"`\\\\$;]{1,256}";
                    }
                }
                leaf "RR_KrngGCrt_Department" {
                    type "string" {
                        pattern "[^\"`\\\\$;]{1,256}";
                    }
                }
                leaf "RR_KrngGCrt_Location" {
                    type "string" {
                        pattern "[^\"`\\\\$;]{1,256}";
                    }
                }
                leaf "RR_KrngGCrt_State" {
                    type "string" {
                        pattern "[^\"`\\\\$;]{1,256}";
                    }
                }
                leaf "RR_KrngGCrt_CountryCode" {
                    when "not (/config_data/main/KrngGenCert/RR_KrngGCrt_Country != 'LB_KrngGCrt_Country_Other')";
                    type "string" {
                        pattern "[A-Z][A-Z]";
                    }
                }
                leaf "RR_KrngGCrt_CommonName" {
                    type "string" {
                        pattern "[^\"`\\\\$;]{1,256}";
                    }
                }
                leaf "RR_KrngGCrt_Email" {
                    type "string" {
                        pattern "[^\"`\\\\$;]{1,256}";
                    }
                }
                leaf "RR_KrngGCrt_ExpPeriod" {
                    type "uint16" {
                        range "7..36500";
                    }
                }
            }
            container "KrngServices" {
                leaf "RR_KrngSrv_LocalCA" {
                    type "lbox_off_on";
                }
            }
            container "KrngLocalCA" {
                when "not (/config_data/main/KrngServices/RR_KrngSrv_LocalCA != 'On')";
                leaf "RR_KrngLCA_KeyId" {
                    type "string" {
                        pattern "[a-zA-Z0-9_]{0,128}";
                    }
                }
                leaf "RR_KrngLCA_CertId" {
                    type "string" {
                        pattern "[a-zA-Z0-9_]{0,128}";
                    }
                }
            }
            container "CnfSecurity" {
                leaf "RR_CnfSec_Pass_Required" {
                    type "lbox_off_on";
                }
                leaf "RR_CnfSec_Pass_MinLCase" {
                    type "uint8" {
                        range "0..5";
                    }
                }
                leaf "RR_CnfSec_Pass_MinUCase" {
                    type "uint8" {
                        range "0..5";
                    }
                }
                leaf "RR_CnfSec_Pass_MinDigit" {
                    type "uint8" {
                        range "0..5";
                    }
                }
                leaf "RR_CnfSec_Pass_MinSpec" {
                    type "uint8" {
                        range "0..5";
                    }
                }
                leaf "RR_CnfSec_Pass_MinLen" {
                    type "uint8" {
                        range "5..64";
                    }
                }
            }
            container "UsbDisc" {
                leaf "RR_UsbDisc_FwEnable" {
                    type "lbox_off_on";
                }
            }
            container "SDK" {
                leaf "RR_Sdk_Enable" {
                    type "lbox_off_on";
                }
            }
            container "MqttBroker" {
                leaf "RR_MqttBroker_Enable" {
                    type "enumeration" {
                        enum "Off" {
                            value "0";
                        }
                        enum "On" {
                            value "1";
                        }
                    }
                    must "not ((. = 'On' and (/config_data/device/DeviceSwKey/RR_SwKey_Flag_mqtt != 'On')))";
                }
                leaf "RR_MqttBroker_QueueQoS0Messages" {
                    when "not (/config_data/main/MqttBroker/RR_MqttBroker_Enable != 'On')";
                    type "lbox_off_on";
                }
                leaf "RR_MqttBroker_RetainAvailable" {
                    when "not (/config_data/main/MqttBroker/RR_MqttBroker_Enable != 'On')";
                    type "lbox_off_on";
                }
                leaf "RR_MqttBroker_UpgradeOutgoingQoS" {
                    when "not (/config_data/main/MqttBroker/RR_MqttBroker_Enable != 'On')";
                    type "lbox_off_on";
                }
                leaf "RR_MqttBroker_BridgeEnable" {
                    when "not (/config_data/main/MqttBroker/RR_MqttBroker_Enable != 'On')";
                    type "lbox_off_on";
                }
            }
            container "MqttListener" {
                when "not (/config_data/main/MqttBroker/RR_MqttBroker_Enable != 'On')";
                leaf "RR_MqttListener_MaxQoS" {
                    type "lbox_mqtt_qos";
                }
                leaf "RR_MqttListener_EnableNonSecurePort" {
                    type "lbox_off_on";
                }
                leaf "RR_MqttListener_ServerCertificateSource" {
                    type "lbox_default_user";
                }
                leaf "RR_MqttListener_Port" {
                    when "not (/config_data/main/MqttListener/RR_MqttListener_EnableNonSecurePort != 'On')";
                    type "lim_udp_port";
                }
                leaf "RR_MqttListener_SecurePort" {
                    type "lim_udp_port";
                }
                leaf "RR_MqttListener_ServerKeyId" {
                    when "not (/config_data/main/MqttListener/RR_MqttListener_ServerCertificateSource != 'LB_default_user_User')";
                    type "string" {
                        pattern "[a-zA-Z0-9_]{0,128}";
                    }
                }
                leaf "RR_MqttListener_ServerCertId" {
                    when "not (/config_data/main/MqttListener/RR_MqttListener_ServerCertificateSource != 'LB_default_user_User')";
                    type "string" {
                        pattern "[a-zA-Z0-9_]{0,128}";
                    }
                }
                leaf "RR_MqttListener_CACertId" {
                    when "not (/config_data/main/MqttListener/RR_MqttListener_ServerCertificateSource != 'LB_default_user_User')";
                    type "string" {
                        pattern "[a-zA-Z0-9_]{0,128}";
                    }
                }
            }
            container "MqttBridge" {
                when "not ((/config_data/main/MqttBroker/RR_MqttBroker_Enable != 'On') or (/config_data/main/MqttBroker/RR_MqttBroker_BridgeEnable != 'On'))";
                leaf "RR_MqttBridge_ProtocolVersion" {
                    type "lbox_mqtt_protocol_version";
                }
                leaf "RR_MqttBridge_OutgoingRetain" {
                    type "lbox_off_on";
                }
                leaf "RR_MqttBridge_EnableSecureBridge" {
                    type "lbox_off_on";
                }
                leaf "RR_MqttBridge_Port" {
                    type "lim_udp_port";
                }
                leaf "RR_MqttBridge_ConnectionAddress" {
                    type "inet:ipv4-address";
                }
                leaf "RR_MqttBridge_ConnectionName" {
                    type "string" {
                        pattern "[a-zA-Z0-9_-]{0,64}";
                    }
                }
                leaf "RR_MqttBridge_RemoteClientID" {
                    type "string" {
                        pattern "[a-zA-Z0-9_-]{0,64}";
                    }
                }
                leaf "RR_MqttBridge_RemotePassword" {
                    type "string" {
                        pattern "[^\"`\\\\$;]{0,128}";
                    }
                }
                leaf "RR_MqttBridge_RemoteUsername" {
                    type "string" {
                        pattern "[a-zA-Z0-9_-]{0,64}";
                    }
                }
                leaf "RR_MqttBridge_KeyId" {
                    when "not (/config_data/main/MqttBridge/RR_MqttBridge_EnableSecureBridge != 'On')";
                    type "string" {
                        pattern "[a-zA-Z0-9_]{0,128}";
                    }
                }
                leaf "RR_MqttBridge_CertId" {
                    when "not (/config_data/main/MqttBridge/RR_MqttBridge_EnableSecureBridge != 'On')";
                    type "string" {
                        pattern "[a-zA-Z0-9_]{0,128}";
                    }
                }
                leaf "RR_MqttBridge_CACertId" {
                    when "not (/config_data/main/MqttBridge/RR_MqttBridge_EnableSecureBridge != 'On')";
                    type "string" {
                        pattern "[a-zA-Z0-9_]{0,128}";
                    }
                }
            }
            list "RR_S_TABLE_LanInterfaces" {
                key "ID";
                max-elements "16";
                leaf "ID" {
                    type "lim_uint_16";
                }
                leaf "LanIface_Name" {
                    type "string" {
                        pattern "[a-zA-Z0-9_-]{1,12}";
                    }
                    mandatory "true";
                }
                leaf "LanIface_ItActive" {
                    type "lbox_off_on";
                    default "On";
                }
                leaf "LanIface_BridgeWithRadio" {
                    when "not ((/config_data/device/DeviceHw/RR_DynHw_Primary_Radio != 'On') or (/config_data/main/RadioInterface/RR_RadioIfMode != 'Bridge'))";
                    type "lbox_off_on";
                    default "Off";
                }
                leaf "LanIface_MngEn" {
                    type "lbox_off_on";
                    default "On";
                }
                leaf "LanIface_StpEn" {
                    when "not (/config_data/main/STP/RR_STP_Ena != 'On')";
                    type "lbox_off_on";
                    default "Off";
                }
                leaf "LanIface_RmtAccEn" {
                    when "not (/config_data/main/UserAccess/RR_UsAcc_RmtAccess_Enable != 'On')";
                    type "lbox_off_on";
                    default "Off";
                }
                leaf "LanIface_Note" {
                    type "string" {
                        pattern "[^\"`\\\\$;]{0,42}";
                    }
                    default "";
                }
                leaf "LanIface_MtuMode" {
                    type "lbox_auto_limited";
                    default "LB_auto_limited_V_Automatic";
                }
                leaf "LanIface_MaxMtu" {
                    when "not (../LanIface_MtuMode != 'LB_auto_limited_V_Limited')";
                    type "uint16" {
                        range "74..1500";
                    }
                    default "1500";
                }
            }
            list "RR_S_TABLE_LanIfacePorts" {
                key "ID";
                max-elements "32";
                leaf "ID" {
                    type "lim_uint_16";
                }
                leaf "ID_Parent" {
                    type "lim_uint_16";
                    default "0";
                }
                leaf "LanIfPort_ItActive" {
                    type "enumeration" {
                        enum "Off" {
                            value "0";
                        }
                        enum "On" {
                            value "1";
                        }
                    }
                    must "not ((. = 'On' and (((../LanIfPort_PortId = 'ETH5') and (/config_data/main/ExtensionPorts/RR_PortSfpEnable != 'On')) or ((../LanIfPort_PortId = 'ETH1') and (/config_data/main/EthPorts/RR_EthPort_1_Enable != 'On')) or ((../LanIfPort_PortId = 'ETH2') and (/config_data/main/EthPorts/RR_EthPort_2_Enable != 'On')) or ((../LanIfPort_PortId = 'ETH3') and (/config_data/main/EthPorts/RR_EthPort_3_Enable != 'On')) or ((../LanIfPort_PortId = 'ETH4') and (/config_data/main/EthPorts/RR_EthPort_4_Enable != 'On')))))";
                    default "On";
                }
                leaf "LanIfPort_PortId" {
                    type "enumeration" {
                        enum "VLAN" {
                            value "0";
                        }
                        enum "ETH1" {
                            value "1";
                        }
                        enum "ETH2" {
                            value "2";
                        }
                        enum "ETH3" {
                            value "3";
                        }
                        enum "ETH4" {
                            value "4";
                        }
                        enum "ETH5" {
                            value "5";
                        }
                    }
                    must "not ((. = 'ETH1' and (/config_data/device/DeviceHw/RR_DynHw_Port_Eth_Cnt <= 0)) or (. = 'ETH2' and (/config_data/device/DeviceHw/RR_DynHw_Port_Eth_Cnt <= 1)) or (. = 'ETH3' and (/config_data/device/DeviceHw/RR_DynHw_Port_Eth_Cnt <= 2)) or (. = 'ETH4' and (/config_data/device/DeviceHw/RR_DynHw_Port_Eth_Cnt <= 3)) or (. = 'ETH5' and (/config_data/device/DeviceHw/RR_DynHw_Port_Sfp != 'On')))";
                    default "ETH1";
                }
                leaf "LanIfPort_VlanRowId" {
                    when "not (../LanIfPort_PortId != 'VLAN')";
                    type "lim_uint_16";
                    default "0";
                }
            }
            list "RR_S_TABLE_LanIfaceLanAddresses" {
                key "ID";
                max-elements "32";
                leaf "ID" {
                    type "lim_uint_16";
                }
                leaf "ID_Parent" {
                    type "lim_uint_16";
                    default "0";
                }
                leaf "LanIfAddr_ItActive" {
                    type "lbox_off_on";
                    default "On";
                }
                leaf "LanIfAddr_IsVirtual" {
                    when "not ((/config_data/device/DeviceHw/RR_DynHw_HotStandby != 'On') or (/config_data/main/HotStdby/RR_HotStdby_Enable != 'On'))";
                    type "lbox_off_on";
                    default "Off";
                }
                leaf "LanIfAddr_IpMask" {
                    type "lim_ipv4_mask";
                    default "24";
                }
                leaf "LanIfAddr_Note" {
                    type "string" {
                        pattern "[^\"`\\\\$;]{0,42}";
                    }
                    default "";
                }
                leaf "LanIfAddr_IpAddr" {
                    type "inet:ipv4-address";
                    default "0.0.0.0";
                }
            }
            list "RR_S_TABLE_LanIfaceVlans" {
                key "ID";
                max-elements "32";
                leaf "ID" {
                    type "lim_uint_16";
                }
                leaf "ID_Parent" {
                    type "lim_uint_16";
                    default "0";
                }
                leaf "LanVlan_ItActive" {
                    type "lbox_off_on";
                    default "On";
                }
                leaf "LanVlan_MngEn" {
                    type "lbox_off_on";
                    default "On";
                }
                leaf "LanVlan_VlanPrioMapping" {
                    when "not (/config_data/main/Networking/RR_QoSMode != 'On')";
                    type "lbox_off_on";
                    default "Off";
                }
                leaf "LanVlan_RmtAccEn" {
                    when "not (/config_data/main/UserAccess/RR_UsAcc_RmtAccess_Enable != 'On')";
                    type "lbox_off_on";
                    default "Off";
                }
                leaf "LanVlan_VlanId" {
                    type "lim_vlan_id";
                    default "1";
                }
                leaf "LanVlan_Note" {
                    type "string" {
                        pattern "[^\"`\\\\$;]{0,42}";
                    }
                    default "";
                }
                leaf "LanVlan_MtuMode" {
                    type "lbox_auto_limited";
                    default "LB_auto_limited_V_Automatic";
                }
                leaf "LanVlan_MaxMtu" {
                    when "not (../LanVlan_MtuMode != 'LB_auto_limited_V_Limited')";
                    type "uint16" {
                        range "70..1496";
                    }
                    default "1496";
                }
            }
            list "RR_S_TABLE_LanIfaceVlanAddresses" {
                key "ID";
                max-elements "32";
                leaf "ID" {
                    type "lim_uint_16";
                }
                leaf "ID_Parent" {
                    type "lim_uint_16";
                    default "0";
                }
                leaf "LanIfAddr_ItActive" {
                    type "lbox_off_on";
                    default "On";
                }
                leaf "LanIfAddr_IsVirtual" {
                    when "not ((/config_data/device/DeviceHw/RR_DynHw_HotStandby != 'On') or (/config_data/main/HotStdby/RR_HotStdby_Enable != 'On'))";
                    type "lbox_off_on";
                    default "Off";
                }
                leaf "LanIfAddr_IpMask" {
                    type "lim_ipv4_mask";
                    default "24";
                }
                leaf "LanIfAddr_Note" {
                    type "string" {
                        pattern "[^\"`\\\\$;]{0,42}";
                    }
                    default "";
                }
                leaf "LanIfAddr_IpAddr" {
                    type "inet:ipv4-address";
                    default "0.0.0.0";
                }
            }
            list "RR_S_TABLE_RadioBabelFltRules" {
                when "not ((/config_data/device/DeviceHw/RR_DynHw_Primary_Radio != 'On') or (/config_data/main/RadioInterface/RR_RadioIfMode != 'Router') or (/config_data/main/Networking/RR_AdvancedDynRouting != 'On') or (/config_data/main/AdvDynamicRouting/RR_ADR_BabelEn != 'On') or (/config_data/main/RadioInterface/RR_RadioBabelFilterEn != 'On'))";
                key "ID";
                max-elements "512";
                leaf "ID" {
                    type "lim_uint_16";
                }
                leaf "RadioBblFltR_ItActive" {
                    type "lbox_off_on";
                    default "On";
                }
                leaf "RadioBblFltR_Note" {
                    type "string" {
                        pattern "[^\"`\\\\$;]{0,42}";
                    }
                    default "";
                }
                leaf "RadioBblFltR_RadioSrcAddr" {
                    type "inet:ipv4-address";
                    default "0.0.0.0";
                }
                leaf "RadioBblFltR_RssThr_Soft" {
                    type "lim_babelflt_rss";
                    must ". <= ../RadioBblFltR_RssThr_Hard" {
                        error-message "valmsg_it_RadioBblFltR_RssThr_Soft";
                    }
                    default "110";
                }
                leaf "RadioBblFltR_RssThr_Hard" {
                    type "lim_babelflt_rss";
                    must ". >= ../RadioBblFltR_RssThr_Soft" {
                        error-message "valmsg_it_RadioBblFltR_RssThr_Hard";
                    }
                    default "130";
                }
                leaf "RadioBblFltR_MseThr_Soft" {
                    type "lim_babelflt_mse";
                    must ". >= ../RadioBblFltR_MseThr_Hard" {
                        error-message "valmsg_it_RadioBblFltR_MseThr_Soft";
                    }
                    default "10";
                }
                leaf "RadioBblFltR_MseThr_Hard" {
                    type "lim_babelflt_mse";
                    must ". <= ../RadioBblFltR_MseThr_Soft" {
                        error-message "valmsg_it_RadioBblFltR_MseThr_Hard";
                    }
                    default "5";
                }
            }
            list "RR_S_TABLE_RadioBDPRemotes" {
                when "not ((/config_data/device/DeviceHw/RR_DynHw_Primary_Radio != 'On') or (/config_data/main/RadioProtocol/RR_RadioAccessProtocol != 'Base driven') or (/config_data/main/RadioProtocolBaseDr/RR_RadioBDP_StationType != 'Base'))";
                key "ID";
                max-elements "512";
                leaf "ID" {
                    type "lim_uint_16";
                }
                leaf "BDPRemotes_Address1" {
                    type "lim_uint_8";
                    must ". <= ../BDPRemotes_Address2" {
                        error-message "valmsg_it_BDPRemotes_Address1";
                    }
                    default "1";
                }
                leaf "BDPRemotes_Address2" {
                    type "lim_uint_8";
                    must ". >= ../BDPRemotes_Address1" {
                        error-message "valmsg_it_BDPRemotes_Address2";
                    }
                    default "1";
                }
                leaf "BDPRemotes_ItActive" {
                    type "lbox_off_on";
                    default "On";
                }
                leaf "BDPRemotes_Type" {
                    type "enumeration" {
                        enum "Direct" {
                            value "0";
                        }
                        enum "Direct & Repeater" {
                            value "1";
                        }
                        enum "Behind Repeater" {
                            value "2";
                        }
                    }
                    default "Direct";
                }
                leaf "BDPRemotes_Ack" {
                    type "lbox_off_on";
                    default "On";
                }
                leaf "BDPRemotes_Retries" {
                    when "not (../BDPRemotes_Ack != 'On')";
                    type "lim_radio_retries";
                    default "3";
                }
                leaf "BDPRemotes_CtsRetries" {
                    when "not (../BDPRemotes_Type = 'Behind Repeater')";
                    type "lim_radio_retries";
                    default "3";
                }
                leaf "BDPRemotes_Modulation" {
                    when "not ((/config_data/main/RadioChannel/RR_RadioACMEn = 'On') and (/config_data/device/DeviceHw/RR_DynHw_Radio_Acm = 'On'))";
                    type "lbox_radio_modulation_M7";
                    must "not ((. = '2CPFSK' and (/config_data/main/RadioChannel/RR_RadioModType != 'FSK')) or (. = '4CPFSK' and (/config_data/main/RadioChannel/RR_RadioModType != 'FSK')) or (. = 'DPSK' and (/config_data/main/RadioChannel/RR_RadioModType != 'QAM')) or (. = 'pi/4DQPSK' and (/config_data/main/RadioChannel/RR_RadioModType != 'QAM')) or (. = 'D8PSK' and (/config_data/main/RadioChannel/RR_RadioModType != 'QAM')) or (. = '16DEQAM' and (/config_data/main/RadioChannel/RR_RadioModType != 'QAM')) or (. = '64QAM' and (/config_data/main/RadioChannel/RR_RadioModType != 'QAM')) or (. = '256QAM' and ((/config_data/main/RadioChannel/RR_RadioModType != 'QAM') or (/config_data/device/DeviceSwKey/RR_SwKey_Flag_radio_modulation_over_64QAM != 'On') or (/config_data/device/DeviceHw/RR_DynHw_Radio_Modulation_Over_64QAM != 'On'))))";
                    default "2CPFSK";
                }
                leaf "BDPRemotes_FEC" {
                    when "not ((/config_data/main/RadioChannel/RR_RadioACMEn = 'On') and (/config_data/device/DeviceHw/RR_DynHw_Radio_Acm = 'On'))";
                    type "lbox_radio_fec_bdp_M9";
                    must "not ((. = '1/1' and ((../BDPRemotes_Modulation = '256QAM') and ((/config_data/main/RadioChannel/RR_RadioChSpacing = '250' and /config_data/main/RadioChannel/RR_RadioChSpacing = '300') or ((/config_data/main/RadioChannel/RR_RadioChSpacing = '200') and (/config_data/main/RadioChannel/RR_RadioChOccupied = '200'))))) or (. = '5/6' and (../BDPRemotes_Modulation != '64QAM' and ../BDPRemotes_Modulation != '256QAM')) or (. = '2/3' and (../BDPRemotes_Modulation != '64QAM' and ../BDPRemotes_Modulation != '256QAM')))";
                    default "1/1";
                }
                leaf "BDPRemotes_RelayAddr" {
                    when "not (../BDPRemotes_Type != 'Behind Repeater')";
                    type "lim_uint_8";
                    default "1";
                }
                leaf "BDPRemotes_Note" {
                    type "string" {
                        pattern "[^\"`\\\\$;]{0,42}";
                    }
                    default "";
                }
            }
            list "RR_S_TABLE_RadioFlexLinkOpts" {
                when "not ((/config_data/device/DeviceHw/RR_DynHw_Primary_Radio != 'On') or (/config_data/main/RadioProtocol/RR_RadioAccessProtocol != 'Flexible'))";
                key "ID";
                max-elements "512";
                leaf "ID" {
                    type "lim_uint_16";
                }
                leaf "FlexLinkOpt_ItActive" {
                    type "lbox_off_on";
                    default "On";
                }
                leaf "FlexLinkOpt_Ack" {
                    type "lbox_off_on";
                    default "On";
                }
                leaf "FlexLinkOpt_Retries" {
                    when "not (../FlexLinkOpt_Ack != 'On')";
                    type "lim_radio_retries";
                    default "3";
                }
                leaf "FlexLinkOpt_Modulation" {
                    when "not ((/config_data/main/RadioChannel/RR_RadioACMEn = 'On') and (/config_data/device/DeviceHw/RR_DynHw_Radio_Acm = 'On'))";
                    type "lbox_radio_modulation_M7";
                    must "not ((. = '2CPFSK' and (/config_data/main/RadioChannel/RR_RadioModType != 'FSK')) or (. = '4CPFSK' and (/config_data/main/RadioChannel/RR_RadioModType != 'FSK')) or (. = 'DPSK' and (/config_data/main/RadioChannel/RR_RadioModType != 'QAM')) or (. = 'pi/4DQPSK' and (/config_data/main/RadioChannel/RR_RadioModType != 'QAM')) or (. = 'D8PSK' and (/config_data/main/RadioChannel/RR_RadioModType != 'QAM')) or (. = '16DEQAM' and (/config_data/main/RadioChannel/RR_RadioModType != 'QAM')) or (. = '64QAM' and (/config_data/main/RadioChannel/RR_RadioModType != 'QAM')) or (. = '256QAM' and ((/config_data/main/RadioChannel/RR_RadioModType != 'QAM') or (/config_data/device/DeviceSwKey/RR_SwKey_Flag_radio_modulation_over_64QAM != 'On') or (/config_data/device/DeviceHw/RR_DynHw_Radio_Modulation_Over_64QAM != 'On'))))";
                    default "2CPFSK";
                }
                leaf "FlexLinkOpt_FEC" {
                    when "not ((/config_data/main/RadioChannel/RR_RadioACMEn = 'On') and (/config_data/device/DeviceHw/RR_DynHw_Radio_Acm = 'On'))";
                    type "lbox_radio_fec_flex_M9";
                    must "not ((. = '1/1' and ((../FlexLinkOpt_Modulation = '256QAM') and ((/config_data/main/RadioChannel/RR_RadioChSpacing = '250' and /config_data/main/RadioChannel/RR_RadioChSpacing = '300') or ((/config_data/main/RadioChannel/RR_RadioChSpacing = '200') and (/config_data/main/RadioChannel/RR_RadioChOccupied = '200'))))) or (. = '5/6' and (../FlexLinkOpt_Modulation != '64QAM' and ../FlexLinkOpt_Modulation != '256QAM')) or (. = '2/3' and (../FlexLinkOpt_Modulation != '64QAM' and ../FlexLinkOpt_Modulation != '256QAM')))";
                    default "1/1";
                }
                leaf "FlexLinkOpt_Note" {
                    type "string" {
                        pattern "[^\"`\\\\$;]{0,42}";
                    }
                    default "";
                }
                leaf "FlexLinkOpt_RadioDstAddr" {
                    type "inet:ipv4-address";
                    default "0.0.0.0";
                }
            }
            list "RR_S_TABLE_CellularProfilesMain" {
                when "not ((/config_data/device/DeviceHw/RR_DynHw_Primary_Cellular != 'On') or (/config_data/main/Cellular/RR_CellMain_Enable != 'On'))";
                key "ID";
                max-elements "8";
                min-elements "1";
                ordered-by "user";
                leaf "ID" {
                    type "lim_uint_16";
                }
                leaf "CellProfMain_ItActive" {
                    type "lbox_off_on";
                    default "On";
                }
                leaf "CellProfMain_Network" {
                    type "lbox_cellular_network";
                    default "Automatic";
                }
                leaf "CellProfMain_PreferredSvc" {
                    when "not (/config_data/device/DeviceHw/RR_DynHw_Cell_Main_SvcConv != 'On')";
                    type "lbox_cellular_Main_preferred_svc_M2";
                    must "not ((. = 'LB_cell_pref_svc_2g_first' and (/config_data/device/DeviceHw/RR_DynHw_Cell_Main_PrefSvc2gFirst != 'On')) or (. = 'LB_cell_pref_svc_2g_only' and ((/config_data/device/DeviceHw/RR_DynHw_Cell_Main_PrefSvc2gOnly != 'On') or ((/config_data/device/DeviceHw/RR_DynHw_Cell_Main_PrefSvc2gFirst = 'On') and (../CellProfMain_Network = 'Prefer manual')))) or (. = 'LB_cell_pref_svc_3g_first' and (/config_data/device/DeviceHw/RR_DynHw_Cell_Main_PrefSvc3gFirst != 'On')) or (. = 'LB_cell_pref_svc_3g_only' and ((/config_data/device/DeviceHw/RR_DynHw_Cell_Main_PrefSvc3gOnly != 'On') or (((/config_data/device/DeviceHw/RR_DynHw_Cell_Main_PrefSvc3gFirst = 'On') or (/config_data/device/DeviceHw/RR_DynHw_Cell_Main_PrefSvc3g4g5gOnly = 'On')) and (../CellProfMain_Network = 'Prefer manual')))) or (. = 'LB_cell_pref_svc_2g_3g_only' and ((/config_data/device/DeviceHw/RR_DynHw_Cell_Main_PrefSvc2g3gOnly != 'On') or (((/config_data/device/DeviceHw/RR_DynHw_Cell_Main_PrefSvc2gFirst = 'On') or (/config_data/device/DeviceHw/RR_DynHw_Cell_Main_PrefSvc3gFirst = 'On')) and (../CellProfMain_Network = 'Prefer manual')))) or (. = 'LB_cell_pref_svc_4g_first' and (/config_data/device/DeviceHw/RR_DynHw_Cell_Main_PrefSvc4gFirst != 'On')) or (. = 'LB_cell_pref_svc_4g_only' and ((/config_data/device/DeviceHw/RR_DynHw_Cell_Main_PrefSvc4gOnly != 'On') or (((/config_data/device/DeviceHw/RR_DynHw_Cell_Main_PrefSvc4gFirst = 'On') or (/config_data/device/DeviceHw/RR_DynHw_Cell_Main_PrefSvc3g4g5gOnly = 'On')) and (../CellProfMain_Network = 'Prefer manual')))) or (. = 'LB_cell_pref_svc_3g_4g_only' and ((/config_data/device/DeviceHw/RR_DynHw_Cell_Main_PrefSvc3g4gOnly != 'On') or (((/config_data/device/DeviceHw/RR_DynHw_Cell_Main_PrefSvc3gFirst = 'On') or (/config_data/device/DeviceHw/RR_DynHw_Cell_Main_PrefSvc4gFirst = 'On') or (/config_data/device/DeviceHw/RR_DynHw_Cell_Main_PrefSvc3g4g5gOnly = 'On')) and (../CellProfMain_Network = 'Prefer manual')))) or (. = 'LB_cell_pref_svc_5g_only' and ((/config_data/device/DeviceHw/RR_DynHw_Cell_Main_PrefSvc5gOnly != 'On') or ((/config_data/device/DeviceHw/RR_DynHw_Cell_Main_PrefSvc3g4g5gOnly = 'On') and (../CellProfMain_Network = 'Prefer manual')))) or (. = 'LB_cell_pref_svc_3g_5g_only' and ((/config_data/device/DeviceHw/RR_DynHw_Cell_Main_PrefSvc3g5gOnly != 'On') or (((/config_data/device/DeviceHw/RR_DynHw_Cell_Main_PrefSvc3gFirst = 'On') or (/config_data/device/DeviceHw/RR_DynHw_Cell_Main_PrefSvc3g4g5gOnly = 'On')) and (../CellProfMain_Network = 'Prefer manual')))) or (. = 'LB_cell_pref_svc_4g_5g_only' and ((/config_data/device/DeviceHw/RR_DynHw_Cell_Main_PrefSvc4g5gOnly != 'On') or (((/config_data/device/DeviceHw/RR_DynHw_Cell_Main_PrefSvc4gFirst = 'On') or (/config_data/device/DeviceHw/RR_DynHw_Cell_Main_PrefSvc3g4g5gOnly = 'On')) and (../CellProfMain_Network = 'Prefer manual')))) or (. = 'LB_cell_pref_svc_3g_4g_5g_only' and (/config_data/device/DeviceHw/RR_DynHw_Cell_Main_PrefSvc3g4g5gOnly != 'On')))";
                    default "LB_cell_pref_svc_4g_first";
                }
                leaf "CellProfMain_ComprHdr" {
                    type "lbox_off_on";
                    default "Off";
                }
                leaf "CellProfMain_ComprData" {
                    type "lbox_off_on";
                    default "Off";
                }
                leaf "CellProfMain_Authentication" {
                    type "lbox_cellular_authentication";
                    default "None";
                }
                leaf "CellProfMain_SimUsed" {
                    type "lbox_cellular_sim_select";
                    default "SIM1";
                }
                leaf "CellProfMain_PreferredSvcLpwan" {
                    when "not (/config_data/device/DeviceHw/RR_DynHw_Cell_Main_SvcLpwan != 'On')";
                    type "lbox_cellular_Main_preferred_svc_lpwan_M2";
                    must "not ((. = 'LB_cell_pref_svc_lpwan_Lte_cat_m_first' and (/config_data/device/DeviceHw/RR_DynHw_Cell_Main_PrefSvcCatMFirst != 'On')) or (. = 'LB_cell_pref_svc_lpwan_Lte_cat_m_only' and ((/config_data/device/DeviceHw/RR_DynHw_Cell_Main_PrefSvcCatMOnly != 'On') or ((/config_data/device/DeviceHw/RR_DynHw_Cell_Main_PrefSvcCatMFirst = 'On') and (../CellProfMain_Network = 'Prefer manual')))) or (. = 'LB_cell_pref_svc_lpwan_Lte_cat_nb_first' and (/config_data/device/DeviceHw/RR_DynHw_Cell_Main_PrefSvcCatNbFirst != 'On')) or (. = 'LB_cell_pref_svc_lpwan_Lte_cat_nb_only' and ((/config_data/device/DeviceHw/RR_DynHw_Cell_Main_PrefSvcCatNbOnly != 'On') or ((/config_data/device/DeviceHw/RR_DynHw_Cell_Main_PrefSvcCatNbFirst = 'On') and (../CellProfMain_Network = 'Prefer manual')))))";
                    default "LB_cell_pref_svc_lpwan_Lte_cat_m_only";
                }
                leaf "CellProfMain_Note" {
                    type "string" {
                        pattern "[^\"`\\\\$;]{0,42}";
                    }
                    default "";
                }
                leaf "CellProfMain_ManualPlmn" {
                    when "not (../CellProfMain_Network != 'Prefer manual' and ../CellProfMain_Network != 'Lock to manual')";
                    type "string" {
                        pattern "[0-9]{1,10}";
                    }
                    default "00000";
                }
                leaf "CellProfMain_APN" {
                    type "string" {
                        pattern "(([a-zA-Z0-9]|([a-zA-Z0-9][a-zA-Z0-9-]{0,61}[a-zA-Z0-9]))(\\.([a-zA-Z0-9]|([a-zA-Z0-9][a-zA-Z0-9-]{0,61}[a-zA-Z0-9])))*)?";
                    }
                    must "string-length(.) <= 99" {
                        error-message "valmsg_it_CellProfMain_APN";
                    }
                    default "";
                }
                leaf "CellProfMain_Username" {
                    when "not (../CellProfMain_Authentication = 'None')";
                    type "string" {
                        pattern "[^\"`\\\\$;]{0,50}";
                    }
                    default "";
                }
                leaf "CellProfMain_Password" {
                    when "not (../CellProfMain_Authentication = 'None')";
                    type "string" {
                        pattern "[^\"`\\\\$;]{0,50}";
                    }
                    default "";
                }
                leaf "CellProfMain_Mtu" {
                    when "not ((/config_data/device/DeviceHw/RR_DynHw_Cell_Main_SvcLpwan != 'Off') and (../CellProfMain_PreferredSvcLpwan != 'LB_cell_pref_svc_lpwan_Lte_cat_m_only'))";
                    type "uint16" {
                        range "70..1500";
                    }
                    must ". >= /config_data/device/DeviceHw/RR_DynHw_Cell_Main_MtuMin" {
                        error-message "valmsg_it_CellProfMain_MtuMin";
                    }
                    default "1500";
                }
            }
            list "RR_S_TABLE_CellularProfilesAux" {
                when "not ((/config_data/device/DeviceHw/RR_DynHw_Module_Cellular != 'On') or (/config_data/main/Cellular/RR_CellAux_Enable != 'On'))";
                key "ID";
                max-elements "8";
                min-elements "1";
                ordered-by "user";
                leaf "ID" {
                    type "lim_uint_16";
                }
                leaf "CellProfAux_ItActive" {
                    type "lbox_off_on";
                    default "On";
                }
                leaf "CellProfAux_Network" {
                    type "lbox_cellular_network";
                    default "Automatic";
                }
                leaf "CellProfAux_PreferredSvc" {
                    when "not (/config_data/device/DeviceHw/RR_DynHw_Cell_Ext_SvcConv != 'On')";
                    type "lbox_cellular_Aux_preferred_svc_M2";
                    must "not ((. = 'LB_cell_pref_svc_2g_first' and (/config_data/device/DeviceHw/RR_DynHw_Cell_Ext_PrefSvc2gFirst != 'On')) or (. = 'LB_cell_pref_svc_2g_only' and ((/config_data/device/DeviceHw/RR_DynHw_Cell_Ext_PrefSvc2gOnly != 'On') or ((/config_data/device/DeviceHw/RR_DynHw_Cell_Ext_PrefSvc2gFirst = 'On') and (../CellProfAux_Network = 'Prefer manual')))) or (. = 'LB_cell_pref_svc_3g_first' and (/config_data/device/DeviceHw/RR_DynHw_Cell_Ext_PrefSvc3gFirst != 'On')) or (. = 'LB_cell_pref_svc_3g_only' and ((/config_data/device/DeviceHw/RR_DynHw_Cell_Ext_PrefSvc3gOnly != 'On') or (((/config_data/device/DeviceHw/RR_DynHw_Cell_Ext_PrefSvc3gFirst = 'On') or (/config_data/device/DeviceHw/RR_DynHw_Cell_Ext_PrefSvc3g4g5gOnly = 'On')) and (../CellProfAux_Network = 'Prefer manual')))) or (. = 'LB_cell_pref_svc_2g_3g_only' and ((/config_data/device/DeviceHw/RR_DynHw_Cell_Ext_PrefSvc2g3gOnly != 'On') or (((/config_data/device/DeviceHw/RR_DynHw_Cell_Ext_PrefSvc2gFirst = 'On') or (/config_data/device/DeviceHw/RR_DynHw_Cell_Ext_PrefSvc3gFirst = 'On')) and (../CellProfAux_Network = 'Prefer manual')))) or (. = 'LB_cell_pref_svc_4g_first' and (/config_data/device/DeviceHw/RR_DynHw_Cell_Ext_PrefSvc4gFirst != 'On')) or (. = 'LB_cell_pref_svc_4g_only' and ((/config_data/device/DeviceHw/RR_DynHw_Cell_Ext_PrefSvc4gOnly != 'On') or (((/config_data/device/DeviceHw/RR_DynHw_Cell_Ext_PrefSvc4gFirst = 'On') or (/config_data/device/DeviceHw/RR_DynHw_Cell_Ext_PrefSvc3g4g5gOnly = 'On')) and (../CellProfAux_Network = 'Prefer manual')))) or (. = 'LB_cell_pref_svc_3g_4g_only' and ((/config_data/device/DeviceHw/RR_DynHw_Cell_Ext_PrefSvc3g4gOnly != 'On') or (((/config_data/device/DeviceHw/RR_DynHw_Cell_Ext_PrefSvc3gFirst = 'On') or (/config_data/device/DeviceHw/RR_DynHw_Cell_Ext_PrefSvc4gFirst = 'On') or (/config_data/device/DeviceHw/RR_DynHw_Cell_Ext_PrefSvc3g4g5gOnly = 'On')) and (../CellProfAux_Network = 'Prefer manual')))) or (. = 'LB_cell_pref_svc_5g_only' and ((/config_data/device/DeviceHw/RR_DynHw_Cell_Ext_PrefSvc5gOnly != 'On') or ((/config_data/device/DeviceHw/RR_DynHw_Cell_Ext_PrefSvc3g4g5gOnly = 'On') and (../CellProfAux_Network = 'Prefer manual')))) or (. = 'LB_cell_pref_svc_3g_5g_only' and ((/config_data/device/DeviceHw/RR_DynHw_Cell_Ext_PrefSvc3g5gOnly != 'On') or (((/config_data/device/DeviceHw/RR_DynHw_Cell_Ext_PrefSvc3gFirst = 'On') or (/config_data/device/DeviceHw/RR_DynHw_Cell_Ext_PrefSvc3g4g5gOnly = 'On')) and (../CellProfAux_Network = 'Prefer manual')))) or (. = 'LB_cell_pref_svc_4g_5g_only' and ((/config_data/device/DeviceHw/RR_DynHw_Cell_Ext_PrefSvc4g5gOnly != 'On') or (((/config_data/device/DeviceHw/RR_DynHw_Cell_Ext_PrefSvc4gFirst = 'On') or (/config_data/device/DeviceHw/RR_DynHw_Cell_Ext_PrefSvc3g4g5gOnly = 'On')) and (../CellProfAux_Network = 'Prefer manual')))) or (. = 'LB_cell_pref_svc_3g_4g_5g_only' and (/config_data/device/DeviceHw/RR_DynHw_Cell_Ext_PrefSvc3g4g5gOnly != 'On')))";
                    default "LB_cell_pref_svc_4g_first";
                }
                leaf "CellProfAux_ComprHdr" {
                    type "lbox_off_on";
                    default "Off";
                }
                leaf "CellProfAux_ComprData" {
                    type "lbox_off_on";
                    default "Off";
                }
                leaf "CellProfAux_Authentication" {
                    type "lbox_cellular_authentication";
                    default "None";
                }
                leaf "CellProfAux_SimUsed" {
                    type "lbox_cellular_sim_select";
                    default "SIM1";
                }
                leaf "CellProfAux_PreferredSvcLpwan" {
                    when "not (/config_data/device/DeviceHw/RR_DynHw_Cell_Ext_SvcLpwan != 'On')";
                    type "lbox_cellular_Aux_preferred_svc_lpwan_M2";
                    must "not ((. = 'LB_cell_pref_svc_lpwan_Lte_cat_m_first' and (/config_data/device/DeviceHw/RR_DynHw_Cell_Ext_PrefSvcCatMFirst != 'On')) or (. = 'LB_cell_pref_svc_lpwan_Lte_cat_m_only' and ((/config_data/device/DeviceHw/RR_DynHw_Cell_Ext_PrefSvcCatMOnly != 'On') or ((/config_data/device/DeviceHw/RR_DynHw_Cell_Ext_PrefSvcCatMFirst = 'On') and (../CellProfAux_Network = 'Prefer manual')))) or (. = 'LB_cell_pref_svc_lpwan_Lte_cat_nb_first' and (/config_data/device/DeviceHw/RR_DynHw_Cell_Ext_PrefSvcCatNbFirst != 'On')) or (. = 'LB_cell_pref_svc_lpwan_Lte_cat_nb_only' and ((/config_data/device/DeviceHw/RR_DynHw_Cell_Ext_PrefSvcCatNbOnly != 'On') or ((/config_data/device/DeviceHw/RR_DynHw_Cell_Ext_PrefSvcCatNbFirst = 'On') and (../CellProfAux_Network = 'Prefer manual')))))";
                    default "LB_cell_pref_svc_lpwan_Lte_cat_m_only";
                }
                leaf "CellProfAux_Note" {
                    type "string" {
                        pattern "[^\"`\\\\$;]{0,42}";
                    }
                    default "";
                }
                leaf "CellProfAux_ManualPlmn" {
                    when "not (../CellProfAux_Network != 'Prefer manual' and ../CellProfAux_Network != 'Lock to manual')";
                    type "string" {
                        pattern "[0-9]{1,10}";
                    }
                    default "00000";
                }
                leaf "CellProfAux_APN" {
                    type "string" {
                        pattern "(([a-zA-Z0-9]|([a-zA-Z0-9][a-zA-Z0-9-]{0,61}[a-zA-Z0-9]))(\\.([a-zA-Z0-9]|([a-zA-Z0-9][a-zA-Z0-9-]{0,61}[a-zA-Z0-9])))*)?";
                    }
                    must "string-length(.) <= 99" {
                        error-message "valmsg_it_CellProfAux_APN";
                    }
                    default "";
                }
                leaf "CellProfAux_Username" {
                    when "not (../CellProfAux_Authentication = 'None')";
                    type "string" {
                        pattern "[^\"`\\\\$;]{0,50}";
                    }
                    default "";
                }
                leaf "CellProfAux_Password" {
                    when "not (../CellProfAux_Authentication = 'None')";
                    type "string" {
                        pattern "[^\"`\\\\$;]{0,50}";
                    }
                    default "";
                }
                leaf "CellProfAux_Mtu" {
                    when "not ((/config_data/device/DeviceHw/RR_DynHw_Cell_Ext_SvcLpwan != 'Off') and (../CellProfAux_PreferredSvcLpwan != 'LB_cell_pref_svc_lpwan_Lte_cat_m_only'))";
                    type "uint16" {
                        range "70..1500";
                    }
                    must ". >= /config_data/device/DeviceHw/RR_DynHw_Cell_Ext_MtuMin" {
                        error-message "valmsg_it_CellProfExt_MtuMin";
                    }
                    default "1500";
                }
            }
            list "RR_S_TABLE_CellularSmsPhones" {
                when "not (((/config_data/device/DeviceHw/RR_DynHw_Primary_Cellular != 'On') or (/config_data/device/DeviceHw/RR_DynHw_Cell_Main_Sms != 'On') or (/config_data/main/Cellular/RR_CellMain_Enable != 'On') or ((/config_data/main/CellularMain/RR_CellMain_SmsCommands != 'On') and (/config_data/main/CellularMain/RR_CellMain_SmsNotifications != 'On'))) and ((/config_data/device/DeviceHw/RR_DynHw_Module_Cellular != 'On') or (/config_data/device/DeviceHw/RR_DynHw_Cell_Ext_Sms != 'On') or (/config_data/main/Cellular/RR_CellAux_Enable != 'On') or ((/config_data/main/CellularAux/RR_CellAux_SmsCommands != 'On') and (/config_data/main/CellularAux/RR_CellAux_SmsNotifications != 'On'))))";
                key "ID";
                max-elements "64";
                leaf "ID" {
                    type "lim_uint_16";
                }
                leaf "CellSmsPh_ItActive" {
                    type "lbox_off_on";
                    default "On";
                }
                leaf "CellSmsPh_RecvCommands" {
                    type "lbox_off_on";
                    default "On";
                }
                leaf "CellSmsPh_SendNotifications" {
                    type "lbox_off_on";
                    default "On";
                }
                leaf "CellSmsPh_Note" {
                    type "string" {
                        pattern "[^\"`\\\\$;]{0,42}";
                    }
                    default "";
                }
                leaf "CellSmsPh_Phone" {
                    type "string" {
                        pattern "\\+[0-9]{3,15}";
                    }
                    mandatory "true";
                }
            }
            list "RR_S_TABLE_WifiExtMacAclRules" {
                when "not ((/config_data/device/DeviceHw/RR_DynHw_Module_Wifi != 'On') or (/config_data/main/Wifi/RR_WifiExt_Enable != 'On') or (/config_data/main/WifiExt/RR_WifiExt_OperationType != 'LB_wifi_operation_type_Ap') or (/config_data/main/WifiExt/RR_WifiExt_MacAcl = 'LB_wifi_mac_acl_Off'))";
                key "ID WifiExtMacAcl_MacAddr";
                max-elements "64";
                leaf "ID" {
                    type "lim_uint_16";
                }
                leaf "WifiExtMacAcl_ItActive" {
                    type "lbox_off_on";
                    default "On";
                }
                leaf "WifiExtMacAcl_Note" {
                    type "string" {
                        pattern "[^\"`\\\\$;]{0,42}";
                    }
                    default "";
                }
                leaf "WifiExtMacAcl_MacAddr" {
                    type "yang:mac-address";
                }
                leaf "WifiExtMacAcl_Password" {
                    when "not ((/config_data/main/WifiExt/RR_WifiExt_Security != 'LB_wifi_security_Wpa3') or (/config_data/main/WifiExt/RR_WifiExt_MacAcl != 'LB_wifi_mac_acl_Accept'))";
                    type "string" {
                        pattern "[^\"`\\\\$;]{0,63}";
                    }
                    default "";
                }
            }
            list "RR_S_TABLE_LoopbackAddresses" {
                key "ID";
                max-elements "256";
                leaf "ID" {
                    type "lim_uint_16";
                }
                leaf "LoopAddr_ItActive" {
                    type "lbox_off_on";
                    default "On";
                }
                leaf "LoopAddr_Note" {
                    type "string" {
                        pattern "[^\"`\\\\$;]{0,42}";
                    }
                    default "";
                }
                leaf "LoopAddr_IpAddr" {
                    type "inet:ipv4-address";
                    default "0.0.0.0";
                }
            }
            list "RR_S_TABLE_FirewallL3Rules" {
                when "not (/config_data/main/Networking/RR_FirewallL3Mode != 'On')";
                key "ID";
                max-elements "256";
                ordered-by "user";
                leaf "ID" {
                    type "lim_uint_16";
                }
                leaf "FwallL3_ItActive" {
                    type "enumeration" {
                        enum "Off" {
                            value "0";
                        }
                        enum "On" {
                            value "1";
                        }
                    }
                    must "not ((. = 'On' and (((/config_data/main/EthPorts/RR_EthPort_1_Enable != 'On') and (../FwallL3_DeviceIn = 'ETH1')) or ((/config_data/main/EthPorts/RR_EthPort_2_Enable != 'On') and (../FwallL3_DeviceIn = 'ETH2')) or ((/config_data/main/EthPorts/RR_EthPort_3_Enable != 'On') and (../FwallL3_DeviceIn = 'ETH3')) or ((/config_data/main/EthPorts/RR_EthPort_4_Enable != 'On') and (../FwallL3_DeviceIn = 'ETH4')) or ((/config_data/main/ExtensionPorts/RR_PortSfpEnable != 'On') and (../FwallL3_DeviceIn = 'ETH5')) or ((/config_data/main/Cellular/RR_CellMain_Enable != 'On') and ((../FwallL3_DeviceIn = 'WWAN') or (../FwallL3_DeviceOut = 'WWAN'))) or ((/config_data/main/Cellular/RR_CellAux_Enable != 'On') and (/config_data/main/Wifi/RR_WifiExt_Enable != 'On') and ((../FwallL3_DeviceIn = 'EXT') or (../FwallL3_DeviceOut = 'EXT'))) or ((/config_data/main/ComPort_1/RR_ComPort_1_Protocol != 'PPP') and (/config_data/main/ComPort_2/RR_ComPort_2_Protocol != 'PPP') and (/config_data/main/ComPort_3/RR_ComPort_3_Protocol != 'PPP') and ((../FwallL3_DeviceIn = 'All PPP') or (../FwallL3_DeviceOut = 'All PPP'))) or ((/config_data/main/Networking/RR_PppoeClient_Enable != 'On') and ((../FwallL3_DeviceIn = 'PPPoE client') or (../FwallL3_DeviceOut = 'PPPoE client'))) or ((/config_data/main/VPN/RR_GreL2Enable != 'On') and (../FwallL3_DeviceIn = 'GRE L2')) or ((/config_data/main/VPN/RR_GreL3Enable != 'On') and ((../FwallL3_DeviceIn = 'GRE L3') or (../FwallL3_DeviceOut = 'GRE L3'))) or ((/config_data/main/VPN/RR_OpenVpnEnable != 'On') and ((../FwallL3_DeviceIn = 'OpenVPN L2' and ../FwallL3_DeviceIn = 'OpenVPN L3') or (../FwallL3_DeviceOut = 'OpenVPN L3'))) or ((/config_data/main/HotStdby/RR_HotStdby_Enable != 'On') and ((../FwallL3_DeviceIn = 'HotStandby') or (../FwallL3_DeviceOut = 'HotStandby'))) or ((/config_data/main/RadioInterface/RR_RadioIfMode != 'Router') and (../FwallL3_DeviceOut = 'Radio')))))";
                    default "On";
                }
                leaf "FwallL3_PolicyFlt" {
                    type "lbox_off_on";
                    default "Off";
                }
                leaf "FwallL3_PolDirection" {
                    when "not (../FwallL3_PolicyFlt != 'On')";
                    type "lbox_firewall_pol_direction";
                    default "LB_firewall_pol_direction_V_In";
                }
                leaf "FwallL3_PolPolicy" {
                    when "not (../FwallL3_PolicyFlt != 'On')";
                    type "lbox_firewall_policy";
                    default "LB_firewall_policy_V_None";
                }
                leaf "FwallL3_SrcIpMask" {
                    type "lim_ipv4_mask0";
                    default "0";
                }
                leaf "FwallL3_DstIpMask" {
                    type "lim_ipv4_mask0";
                    default "0";
                }
                leaf "FwallL3_Note" {
                    type "string" {
                        pattern "[^\"`\\\\$;]{0,42}";
                    }
                    default "";
                }
                leaf "FwallL3_Protocol" {
                    type "lbox_l3_protocol";
                    default "All";
                }
                leaf "FwallL3_DeviceOut" {
                    type "lbox_network_devices_log_M8";
                    must "not ((. = 'Radio' and (/config_data/device/DeviceHw/RR_DynHw_Primary_Radio != 'On')) or (. = 'WWAN' and (/config_data/device/DeviceHw/RR_DynHw_Primary_Cellular != 'On')) or (. = 'EXT' and ((/config_data/device/DeviceHw/RR_DynHw_Module_Cellular != 'On') and (/config_data/device/DeviceHw/RR_DynHw_Module_Wifi != 'On'))) or (. = 'HotStandby' and (/config_data/device/DeviceHw/RR_DynHw_HotStandby != 'On')))";
                    default "All";
                }
                leaf "FwallL3_CStateNew" {
                    type "lbox_off_on";
                    default "Off";
                }
                leaf "FwallL3_CStateRel" {
                    type "lbox_off_on";
                    default "Off";
                }
                leaf "FwallL3_CStateEst" {
                    type "lbox_off_on";
                    default "Off";
                }
                leaf "FwallL3_Action" {
                    type "lbox_firewall_action";
                    default "Deny";
                }
                leaf "FwallL3_DeviceIn" {
                    type "lbox_network_devices_log_phy_M9";
                    must "not ((. = 'Radio' and (/config_data/device/DeviceHw/RR_DynHw_Primary_Radio != 'On')) or (. = 'WWAN' and (/config_data/device/DeviceHw/RR_DynHw_Primary_Cellular != 'On')) or (. = 'EXT' and ((/config_data/device/DeviceHw/RR_DynHw_Module_Cellular != 'On') and (/config_data/device/DeviceHw/RR_DynHw_Module_Wifi != 'On'))) or (. = 'ETH1' and (/config_data/device/DeviceHw/RR_DynHw_Port_Eth_Cnt <= 0)) or (. = 'ETH2' and (/config_data/device/DeviceHw/RR_DynHw_Port_Eth_Cnt <= 1)) or (. = 'ETH3' and (/config_data/device/DeviceHw/RR_DynHw_Port_Eth_Cnt <= 2)) or (. = 'ETH4' and (/config_data/device/DeviceHw/RR_DynHw_Port_Eth_Cnt <= 3)) or (. = 'ETH5' and (/config_data/device/DeviceHw/RR_DynHw_Port_Sfp != 'On')) or (. = 'HotStandby' and (/config_data/device/DeviceHw/RR_DynHw_HotStandby != 'On')))";
                    default "All";
                }
                leaf "FwallL3_ProtocolNum" {
                    when "not (../FwallL3_Protocol != 'Other')";
                    type "lim_uint_8_1toFF";
                    default "1";
                }
                leaf "FwallL3_SrcIp" {
                    type "inet:ipv4-address";
                    default "0.0.0.0";
                }
                leaf "FwallL3_SrcPortStart" {
                    when "not (../FwallL3_Protocol != 'UDP' and ../FwallL3_Protocol != 'TCP')";
                    type "lim_udp_port0";
                    must ". <= ../FwallL3_SrcPortEnd" {
                        error-message "valmsg_it_FwallL3_SrcPortStart";
                    }
                    default "0";
                }
                leaf "FwallL3_SrcPortEnd" {
                    when "not (../FwallL3_Protocol != 'UDP' and ../FwallL3_Protocol != 'TCP')";
                    type "lim_udp_port0";
                    must ". >= ../FwallL3_SrcPortStart" {
                        error-message "valmsg_it_FwallL3_SrcPortEnd";
                    }
                    default "0";
                }
                leaf "FwallL3_DstIp" {
                    type "inet:ipv4-address";
                    default "0.0.0.0";
                }
                leaf "FwallL3_DstPortStart" {
                    when "not (../FwallL3_Protocol != 'UDP' and ../FwallL3_Protocol != 'TCP')";
                    type "lim_udp_port0";
                    must ". <= ../FwallL3_DstPortEnd" {
                        error-message "valmsg_tab_FwallL3_DstPortStart";
                    }
                    default "0";
                }
                leaf "FwallL3_DstPortEnd" {
                    when "not (../FwallL3_Protocol != 'UDP' and ../FwallL3_Protocol != 'TCP')";
                    type "lim_udp_port0";
                    must ". >= ../FwallL3_DstPortStart" {
                        error-message "valmsg_tab_FwallL3_DstPortEnd";
                    }
                    default "0";
                }
                leaf "FwallL3_DeviceInName" {
                    when "not (../FwallL3_DeviceIn != 'Other')";
                    type "string" {
                        pattern "[a-zA-Z0-9_.-]{0,16}";
                    }
                    default "";
                }
                leaf "FwallL3_DeviceOutName" {
                    when "not (../FwallL3_DeviceOut != 'Other')";
                    type "string" {
                        pattern "[a-zA-Z0-9_.-]{0,16}";
                    }
                    default "";
                }
                leaf "FwallL3_LogId" {
                    when "not ((/config_data/main/FirewallL3Log/RR_FirewallL3Log_En != 'On') or (../FwallL3_LogEn != 'On'))";
                    type "string" {
                        pattern "[a-zA-Z0-9_-]{0,12}";
                    }
                    default "";
                }
                leaf "FwallL3_LogEn" {
                    when "not (/config_data/main/FirewallL3Log/RR_FirewallL3Log_En != 'On')";
                    type "lbox_off_on";
                    default "Off";
                }
                leaf "FwallL3_LogSeverity" {
                    when "not ((/config_data/main/FirewallL3Log/RR_FirewallL3Log_En != 'On') or (../FwallL3_LogEn != 'On'))";
                    type "lbox_event_severity";
                    default "Notice";
                }
            }
            list "RR_S_TABLE_FirewallL3RulesIn" {
                when "not (/config_data/main/Networking/RR_FirewallL3Mode != 'On')";
                key "ID";
                max-elements "256";
                ordered-by "user";
                leaf "ID" {
                    type "lim_uint_16";
                }
                leaf "FwallL3In_Active" {
                    type "enumeration" {
                        enum "Off" {
                            value "0";
                        }
                        enum "On" {
                            value "1";
                        }
                    }
                    must "not ((. = 'On' and (((/config_data/main/EthPorts/RR_EthPort_1_Enable != 'On') and (../FwallL3In_DeviceIn = 'ETH1')) or ((/config_data/main/EthPorts/RR_EthPort_2_Enable != 'On') and (../FwallL3In_DeviceIn = 'ETH2')) or ((/config_data/main/EthPorts/RR_EthPort_3_Enable != 'On') and (../FwallL3In_DeviceIn = 'ETH3')) or ((/config_data/main/EthPorts/RR_EthPort_4_Enable != 'On') and (../FwallL3In_DeviceIn = 'ETH4')) or ((/config_data/main/ExtensionPorts/RR_PortSfpEnable != 'On') and (../FwallL3In_DeviceIn = 'ETH5')) or ((/config_data/main/Cellular/RR_CellMain_Enable != 'On') and (../FwallL3In_DeviceIn = 'WWAN')) or ((/config_data/main/Cellular/RR_CellAux_Enable != 'On') and (/config_data/main/Wifi/RR_WifiExt_Enable != 'On') and (../FwallL3In_DeviceIn = 'EXT')) or ((/config_data/main/ComPort_1/RR_ComPort_1_Protocol != 'PPP') and (/config_data/main/ComPort_2/RR_ComPort_2_Protocol != 'PPP') and (/config_data/main/ComPort_3/RR_ComPort_3_Protocol != 'PPP') and (../FwallL3In_DeviceIn = 'All PPP')) or ((/config_data/main/Networking/RR_PppoeClient_Enable != 'On') and (../FwallL3In_DeviceIn = 'PPPoE client')) or ((/config_data/main/VPN/RR_GreL2Enable != 'On') and (../FwallL3In_DeviceIn = 'GRE L2')) or ((/config_data/main/VPN/RR_GreL3Enable != 'On') and (../FwallL3In_DeviceIn = 'GRE L3')) or ((/config_data/main/VPN/RR_OpenVpnEnable != 'On') and (../FwallL3In_DeviceIn = 'OpenVPN L2' and ../FwallL3In_DeviceIn = 'OpenVPN L3')) or ((/config_data/main/HotStdby/RR_HotStdby_Enable != 'On') and (../FwallL3In_DeviceIn = 'HotStandby')) or ((/config_data/main/RadioInterface/RR_RadioIfMode != 'Router') and (../FwallL3In_DeviceIn = 'Radio')))))";
                    default "On";
                }
                leaf "FwallL3In_NetService" {
                    type "lbox_net_services";
                    default "Other";
                }
                leaf "FwallL3In_Protocol" {
                    when "not (../FwallL3In_NetService != 'Other')";
                    type "lbox_l3_protocol";
                    default "All";
                }
                leaf "FwallL3In_SrcIpMask" {
                    type "lim_ipv4_mask0";
                    default "0";
                }
                leaf "FwallL3In_Note" {
                    type "string" {
                        pattern "[^\"`\\\\$;]{0,42}";
                    }
                    default "";
                }
                leaf "FwallL3In_ProtocolNum" {
                    when "not ((../FwallL3In_NetService != 'Other') or (../FwallL3In_Protocol != 'Other'))";
                    type "lim_uint_8_1toFF";
                    default "1";
                }
                leaf "FwallL3In_SrcIp" {
                    type "inet:ipv4-address";
                    default "0.0.0.0";
                }
                leaf "FwallL3In_SrcPortStart" {
                    when "not ((../FwallL3In_NetService = 'Other') and (../FwallL3In_Protocol != 'TCP' and ../FwallL3In_Protocol != 'UDP'))";
                    type "lim_udp_port0";
                    must ". <= ../FwallL3In_SrcPortEnd" {
                        error-message "valmsg_it_FwallL3In_SrcPortStart";
                    }
                    default "0";
                }
                leaf "FwallL3In_SrcPortEnd" {
                    when "not ((../FwallL3In_NetService = 'Other') and (../FwallL3In_Protocol != 'TCP' and ../FwallL3In_Protocol != 'UDP'))";
                    type "lim_udp_port0";
                    must ". >= ../FwallL3In_SrcPortStart" {
                        error-message "valmsg_it_FwallL3In_SrcPortEnd";
                    }
                    default "0";
                }
                leaf "FwallL3In_DstIp" {
                    type "inet:ipv4-address";
                    default "0.0.0.0";
                }
                leaf "FwallL3In_DstPortStart" {
                    when "not ((../FwallL3In_NetService != 'Other') or (../FwallL3In_Protocol != 'TCP' and ../FwallL3In_Protocol != 'UDP'))";
                    type "uint16";
                    must ". <= ../FwallL3In_DstPortEnd" {
                        error-message "valmsg_it_FwallL3In_DstPortStart";
                    }
                    default "0";
                }
                leaf "FwallL3In_DstPortEnd" {
                    when "not ((../FwallL3In_NetService != 'Other') or (../FwallL3In_Protocol != 'TCP' and ../FwallL3In_Protocol != 'UDP'))";
                    type "lim_udp_port0";
                    must ". >= ../FwallL3In_DstPortStart" {
                        error-message "valmsg_it_FwallL3In_DstPortEnd";
                    }
                    default "0";
                }
                leaf "FwallL3In_DstIpMask" {
                    type "lim_ipv4_mask0";
                    default "0";
                }
                leaf "FwallL3In_PolicyFlt" {
                    type "lbox_off_on";
                    default "Off";
                }
                leaf "FwallL3In_PolPolicy" {
                    when "not (../FwallL3In_PolicyFlt != 'On')";
                    type "lbox_firewall_policy";
                    default "LB_firewall_policy_V_None";
                }
                leaf "FwallL3In_CStateNew" {
                    type "lbox_off_on";
                    default "Off";
                }
                leaf "FwallL3In_CStateRel" {
                    type "lbox_off_on";
                    default "Off";
                }
                leaf "FwallL3In_CStateEst" {
                    type "lbox_off_on";
                    default "Off";
                }
                leaf "FwallL3In_Action" {
                    type "enumeration" {
                        enum "Deny" {
                            value "0";
                        }
                        enum "Allow" {
                            value "1";
                        }
                        enum "Ban source" {
                            value "2";
                        }
                    }
                    default "Deny";
                }
                leaf "FwallL3In_DeviceIn" {
                    type "lbox_network_devices_log_phy_M9";
                    must "not ((. = 'Radio' and (/config_data/device/DeviceHw/RR_DynHw_Primary_Radio != 'On')) or (. = 'WWAN' and (/config_data/device/DeviceHw/RR_DynHw_Primary_Cellular != 'On')) or (. = 'EXT' and ((/config_data/device/DeviceHw/RR_DynHw_Module_Cellular != 'On') and (/config_data/device/DeviceHw/RR_DynHw_Module_Wifi != 'On'))) or (. = 'ETH1' and (/config_data/device/DeviceHw/RR_DynHw_Port_Eth_Cnt <= 0)) or (. = 'ETH2' and (/config_data/device/DeviceHw/RR_DynHw_Port_Eth_Cnt <= 1)) or (. = 'ETH3' and (/config_data/device/DeviceHw/RR_DynHw_Port_Eth_Cnt <= 2)) or (. = 'ETH4' and (/config_data/device/DeviceHw/RR_DynHw_Port_Eth_Cnt <= 3)) or (. = 'ETH5' and (/config_data/device/DeviceHw/RR_DynHw_Port_Sfp != 'On')) or (. = 'HotStandby' and (/config_data/device/DeviceHw/RR_DynHw_HotStandby != 'On')))";
                    default "All";
                }
                leaf "FwallL3In_DeviceInName" {
                    when "not (../FwallL3In_DeviceIn != 'Other')";
                    type "string" {
                        pattern "[a-zA-Z0-9_.-]{0,16}";
                    }
                    default "";
                }
                leaf "FwallL3In_LogId" {
                    when "not ((/config_data/main/FirewallL3Log/RR_FirewallL3Log_En != 'On') or (../FwallL3In_LogEn != 'On'))";
                    type "string" {
                        pattern "[a-zA-Z0-9_-]{0,12}";
                    }
                    default "";
                }
                leaf "FwallL3In_LogEn" {
                    when "not (/config_data/main/FirewallL3Log/RR_FirewallL3Log_En != 'On')";
                    type "lbox_off_on";
                    default "Off";
                }
                leaf "FwallL3In_LogSeverity" {
                    when "not ((/config_data/main/FirewallL3Log/RR_FirewallL3Log_En != 'On') or (../FwallL3In_LogEn != 'On'))";
                    type "lbox_event_severity";
                    default "Notice";
                }
            }
            list "RR_S_TABLE_FirewallL3RulesOut" {
                when "not (/config_data/main/Networking/RR_FirewallL3Mode != 'On')";
                key "ID";
                max-elements "256";
                ordered-by "user";
                leaf "ID" {
                    type "lim_uint_16";
                }
                leaf "FwallL3Out_Active" {
                    type "enumeration" {
                        enum "Off" {
                            value "0";
                        }
                        enum "On" {
                            value "1";
                        }
                    }
                    must "not ((. = 'On' and (((/config_data/main/Cellular/RR_CellMain_Enable != 'On') and (../FwallL3Out_DeviceOut = 'WWAN')) or ((/config_data/main/Cellular/RR_CellAux_Enable != 'On') and (/config_data/main/Wifi/RR_WifiExt_Enable != 'On') and (../FwallL3Out_DeviceOut = 'EXT')) or ((/config_data/main/ComPort_1/RR_ComPort_1_Protocol != 'PPP') and (/config_data/main/ComPort_2/RR_ComPort_2_Protocol != 'PPP') and (/config_data/main/ComPort_3/RR_ComPort_3_Protocol != 'PPP') and (../FwallL3Out_DeviceOut = 'All PPP')) or ((/config_data/main/Networking/RR_PppoeClient_Enable != 'On') and (../FwallL3Out_DeviceOut = 'PPPoE client')) or ((/config_data/main/VPN/RR_GreL3Enable != 'On') and (../FwallL3Out_DeviceOut = 'GRE L3')) or ((/config_data/main/VPN/RR_OpenVpnEnable != 'On') and (../FwallL3Out_DeviceOut = 'OpenVPN L3')) or ((/config_data/main/HotStdby/RR_HotStdby_Enable != 'On') and (../FwallL3Out_DeviceOut = 'HotStandby')) or ((/config_data/main/RadioInterface/RR_RadioIfMode != 'Router') and (../FwallL3Out_DeviceOut = 'Radio')))))";
                    default "On";
                }
                leaf "FwallL3Out_NetService" {
                    type "lbox_net_services";
                    default "Other";
                }
                leaf "FwallL3Out_Protocol" {
                    when "not (../FwallL3Out_NetService != 'Other')";
                    type "lbox_l3_protocol";
                    default "All";
                }
                leaf "FwallL3Out_DstIpMask" {
                    type "lim_ipv4_mask0";
                    default "0";
                }
                leaf "FwallL3Out_Note" {
                    type "string" {
                        pattern "[^\"`\\\\$;]{0,42}";
                    }
                    default "";
                }
                leaf "FwallL3Out_ProtocolNum" {
                    when "not ((../FwallL3Out_NetService != 'Other') or (../FwallL3Out_Protocol != 'Other'))";
                    type "lim_uint_8_1toFF";
                    default "1";
                }
                leaf "FwallL3Out_SrcIp" {
                    type "inet:ipv4-address";
                    default "0.0.0.0";
                }
                leaf "FwallL3Out_SrcIpMask" {
                    type "lim_ipv4_mask0";
                    default "0";
                }
                leaf "FwallL3Out_DeviceOut" {
                    type "lbox_network_devices_log_M8";
                    must "not ((. = 'Radio' and (/config_data/device/DeviceHw/RR_DynHw_Primary_Radio != 'On')) or (. = 'WWAN' and (/config_data/device/DeviceHw/RR_DynHw_Primary_Cellular != 'On')) or (. = 'EXT' and ((/config_data/device/DeviceHw/RR_DynHw_Module_Cellular != 'On') and (/config_data/device/DeviceHw/RR_DynHw_Module_Wifi != 'On'))) or (. = 'HotStandby' and (/config_data/device/DeviceHw/RR_DynHw_HotStandby != 'On')))";
                    default "All";
                }
                leaf "FwallL3Out_PolicyFlt" {
                    type "lbox_off_on";
                    default "Off";
                }
                leaf "FwallL3Out_PolPolicy" {
                    when "not (../FwallL3Out_PolicyFlt != 'On')";
                    type "lbox_firewall_policy";
                    default "LB_firewall_policy_V_None";
                }
                leaf "FwallL3Out_SrcPortStart" {
                    when "not ((../FwallL3Out_NetService != 'Other') or (../FwallL3Out_Protocol != 'TCP' and ../FwallL3Out_Protocol != 'UDP'))";
                    type "lim_udp_port0";
                    must ". <= ../FwallL3Out_SrcPortEnd" {
                        error-message "valmsg_it_FwallL3Out_SrcPortStart";
                    }
                    default "0";
                }
                leaf "FwallL3Out_SrcPortEnd" {
                    when "not ((../FwallL3Out_NetService != 'Other') or (../FwallL3Out_Protocol != 'TCP' and ../FwallL3Out_Protocol != 'UDP'))";
                    type "lim_udp_port0";
                    must ". >= ../FwallL3Out_SrcPortStart" {
                        error-message "valmsg_it_FwallL3Out_SrcPortEnd";
                    }
                    default "0";
                }
                leaf "FwallL3Out_DstIp" {
                    type "inet:ipv4-address";
                    default "0.0.0.0";
                }
                leaf "FwallL3Out_DstPortStart" {
                    when "not ((../FwallL3Out_NetService = 'Other') and (../FwallL3Out_Protocol != 'TCP' and ../FwallL3Out_Protocol != 'UDP'))";
                    type "lim_udp_port0";
                    must ". <= ../FwallL3Out_DstPortEnd" {
                        error-message "valmsg_it_FwallL3Out_DstPortStart";
                    }
                    default "0";
                }
                leaf "FwallL3Out_DstPortEnd" {
                    when "not ((../FwallL3Out_NetService = 'Other') and (../FwallL3Out_Protocol != 'TCP' and ../FwallL3Out_Protocol != 'UDP'))";
                    type "lim_udp_port0";
                    must ". >= ../FwallL3Out_DstPortStart" {
                        error-message "valmsg_it_FwallL3Out_DstPortEnd";
                    }
                    default "0";
                }
                leaf "FwallL3Out_DeviceOutName" {
                    when "not (../FwallL3Out_DeviceOut != 'Other')";
                    type "string" {
                        pattern "[a-zA-Z0-9_.-]{0,16}";
                    }
                    default "";
                }
                leaf "FwallL3Out_CStateNew" {
                    type "lbox_off_on";
                    default "Off";
                }
                leaf "FwallL3Out_CStateRel" {
                    type "lbox_off_on";
                    default "Off";
                }
                leaf "FwallL3Out_CStateEst" {
                    type "lbox_off_on";
                    default "Off";
                }
                leaf "FwallL3Out_Action" {
                    type "lbox_firewall_action";
                    default "Deny";
                }
                leaf "FwallL3Out_LogEn" {
                    when "not (/config_data/main/FirewallL3Log/RR_FirewallL3Log_En != 'On')";
                    type "lbox_off_on";
                    default "Off";
                }
                leaf "FwallL3Out_LogSeverity" {
                    when "not ((/config_data/main/FirewallL3Log/RR_FirewallL3Log_En != 'On') or (../FwallL3Out_LogEn != 'On'))";
                    type "lbox_event_severity";
                    default "Notice";
                }
                leaf "FwallL3Out_LogId" {
                    when "not ((/config_data/main/FirewallL3Log/RR_FirewallL3Log_En != 'On') or (../FwallL3Out_LogEn != 'On'))";
                    type "string" {
                        pattern "[a-zA-Z0-9_-]{0,12}";
                    }
                    default "";
                }
            }
            list "RR_S_TABLE_FirewallL2AccRules" {
                when "not (/config_data/main/Networking/RR_FirewallL2AccessCtrl = 'Off')";
                key "ID";
                max-elements "128";
                ordered-by "user";
                leaf "ID" {
                    type "lim_uint_16";
                }
                leaf "FwallL2Acc_ItActive" {
                    type "enumeration" {
                        enum "Off" {
                            value "0";
                        }
                        enum "On" {
                            value "1";
                        }
                    }
                    must "not ((. = 'On' and (((/config_data/main/EthPorts/RR_EthPort_1_Enable != 'On') and (../FwallL2Acc_PortIn = 'ETH1')) or ((/config_data/main/EthPorts/RR_EthPort_2_Enable != 'On') and (../FwallL2Acc_PortIn = 'ETH2')) or ((/config_data/main/EthPorts/RR_EthPort_3_Enable != 'On') and (../FwallL2Acc_PortIn = 'ETH3')) or ((/config_data/main/EthPorts/RR_EthPort_4_Enable != 'On') and (../FwallL2Acc_PortIn = 'ETH4')) or ((/config_data/main/ExtensionPorts/RR_PortSfpEnable != 'On') and (../FwallL2Acc_PortIn = 'ETH5')))))";
                    default "On";
                }
                leaf "FwallL2Acc_PortIn" {
                    type "enumeration" {
                        enum "All" {
                            value "0";
                        }
                        enum "ETH1" {
                            value "1";
                        }
                        enum "ETH2" {
                            value "2";
                        }
                        enum "ETH3" {
                            value "3";
                        }
                        enum "ETH4" {
                            value "4";
                        }
                        enum "ETH5" {
                            value "5";
                        }
                    }
                    must "not ((. = 'ETH1' and (/config_data/device/DeviceHw/RR_DynHw_Port_Eth_Cnt <= 0)) or (. = 'ETH2' and (/config_data/device/DeviceHw/RR_DynHw_Port_Eth_Cnt <= 1)) or (. = 'ETH3' and (/config_data/device/DeviceHw/RR_DynHw_Port_Eth_Cnt <= 2)) or (. = 'ETH4' and (/config_data/device/DeviceHw/RR_DynHw_Port_Eth_Cnt <= 3)) or (. = 'ETH5' and (/config_data/device/DeviceHw/RR_DynHw_Port_Sfp != 'On')))";
                    default "All";
                }
                leaf "FwallL2Acc_LogEn" {
                    when "not (/config_data/main/FirewallL2AccLog/RR_FirewallL2AccLog_En != 'On')";
                    type "lbox_off_on";
                    default "Off";
                }
                leaf "FwallL2Acc_LogSeverity" {
                    when "not ((/config_data/main/FirewallL2AccLog/RR_FirewallL2AccLog_En != 'On') or (../FwallL2Acc_LogEn != 'On'))";
                    type "lbox_event_severity";
                    default "Notice";
                }
                leaf "FwallL2Acc_LogId" {
                    when "not ((/config_data/main/FirewallL2AccLog/RR_FirewallL2AccLog_En != 'On') or (../FwallL2Acc_LogEn != 'On'))";
                    type "string" {
                        pattern "[a-zA-Z0-9_-]{0,12}";
                    }
                    default "";
                }
                leaf "FwallL2Acc_Note" {
                    type "string" {
                        pattern "[^\"`\\\\$;]{0,42}";
                    }
                    default "";
                }
                leaf "FwallL2Acc_MAC" {
                    type "yang:mac-address";
                    default "00:00:00:00:00:00";
                }
            }
            list "RR_S_TABLE_FirewallL2RulesFwd" {
                when "not (/config_data/main/Networking/RR_FirewallL2Mode != 'On')";
                key "ID";
                max-elements "256";
                ordered-by "user";
                leaf "ID" {
                    type "lim_uint_16";
                }
                leaf "FwallL2Fwd_ItActive" {
                    type "enumeration" {
                        enum "Off" {
                            value "0";
                        }
                        enum "On" {
                            value "1";
                        }
                    }
                    must "not ((. = 'On' and (((/config_data/main/EthPorts/RR_EthPort_1_Enable != 'On') and ((../FwallL2Fwd_DeviceIn = 'ETH1') or (../FwallL2Fwd_DeviceOut = 'ETH1'))) or ((/config_data/main/EthPorts/RR_EthPort_2_Enable != 'On') and ((../FwallL2Fwd_DeviceIn = 'ETH2') or (../FwallL2Fwd_DeviceOut = 'ETH2'))) or ((/config_data/main/EthPorts/RR_EthPort_3_Enable != 'On') and ((../FwallL2Fwd_DeviceIn = 'ETH3') or (../FwallL2Fwd_DeviceOut = 'ETH3'))) or ((/config_data/main/EthPorts/RR_EthPort_4_Enable != 'On') and ((../FwallL2Fwd_DeviceIn = 'ETH4') or (../FwallL2Fwd_DeviceOut = 'ETH4'))) or ((/config_data/main/ExtensionPorts/RR_PortSfpEnable != 'On') and ((../FwallL2Fwd_DeviceIn = 'ETH5') or (../FwallL2Fwd_DeviceOut = 'ETH5'))) or ((/config_data/main/VPN/RR_GreL2Enable != 'On') and ((../FwallL2Fwd_DeviceIn = 'GRE L2') or (../FwallL2Fwd_DeviceOut = 'GRE L2'))) or ((/config_data/main/VPN/RR_OpenVpnEnable != 'On') and ((../FwallL2Fwd_DeviceIn = 'OpenVPN L2') or (../FwallL2Fwd_DeviceOut = 'OpenVPN L2'))) or ((/config_data/main/RadioInterface/RR_RadioIfMode != 'Bridge') and ((../FwallL2Fwd_DeviceIn = 'Radio') or (../FwallL2Fwd_DeviceOut = 'Radio'))))))";
                    default "On";
                }
                leaf "FwallL2Fwd_VlanEncap" {
                    type "lbox_off_on";
                    default "Off";
                }
                leaf "FwallL2Fwd_VlanId" {
                    when "not (../FwallL2Fwd_VlanEncap != 'On')";
                    type "lim_vlan_id";
                    default "1";
                }
                leaf "FwallL2Fwd_BridgeFilter" {
                    type "lbox_off_on";
                    default "Off";
                }
                leaf "FwallL2Fwd_TrafficLimit" {
                    type "lbox_off_on";
                    default "Off";
                }
                leaf "FwallL2Fwd_Note" {
                    type "string" {
                        pattern "[^\"`\\\\$;]{0,42}";
                    }
                    default "";
                }
                leaf "FwallL2Fwd_EtherType" {
                    type "lbox_l2_protocol";
                    default "LB_l2_protocol_V_All";
                }
                leaf "FwallL2Fwd_SrcFilter" {
                    type "lbox_l2_address_filter";
                    default "LB_l2_address_filter_V_All";
                }
                leaf "FwallL2Fwd_DstFilter" {
                    type "lbox_l2_address_filter";
                    default "LB_l2_address_filter_V_All";
                }
                leaf "FwallL2Fwd_DeviceIn" {
                    type "lbox_network_devices_phy";
                    must "not ((. = 'Radio' and (/config_data/device/DeviceHw/RR_DynHw_Primary_Radio != 'On')) or (. = 'ETH1' and (/config_data/device/DeviceHw/RR_DynHw_Port_Eth_Cnt <= 0)) or (. = 'ETH2' and (/config_data/device/DeviceHw/RR_DynHw_Port_Eth_Cnt <= 1)) or (. = 'ETH3' and (/config_data/device/DeviceHw/RR_DynHw_Port_Eth_Cnt <= 2)) or (. = 'ETH4' and (/config_data/device/DeviceHw/RR_DynHw_Port_Eth_Cnt <= 3)) or (. = 'ETH5' and (/config_data/device/DeviceHw/RR_DynHw_Port_Sfp != 'On')))";
                    default "All";
                }
                leaf "FwallL2Fwd_Action" {
                    type "lbox_firewall_action";
                    default "Deny";
                }
                leaf "FwallL2Fwd_EtherTypeNum" {
                    when "not (../FwallL2Fwd_EtherType != 'LB_l2_protocol_V_Other')";
                    type "uint16" {
                        range "2048..65535";
                    }
                    default "0x0800";
                }
                leaf "FwallL2Fwd_SrcMac" {
                    when "not (../FwallL2Fwd_SrcFilter != 'LB_l2_address_filter_V_Mask')";
                    type "yang:mac-address";
                    default "00:00:00:00:00:00";
                }
                leaf "FwallL2Fwd_SrcMacMask" {
                    when "not (../FwallL2Fwd_SrcFilter != 'LB_l2_address_filter_V_Mask')";
                    type "yang:mac-address";
                    default "00:00:00:00:00:00";
                }
                leaf "FwallL2Fwd_DstMac" {
                    when "not (../FwallL2Fwd_DstFilter != 'LB_l2_address_filter_V_Mask')";
                    type "yang:mac-address";
                    default "00:00:00:00:00:00";
                }
                leaf "FwallL2Fwd_DstMacMask" {
                    when "not (../FwallL2Fwd_DstFilter != 'LB_l2_address_filter_V_Mask')";
                    type "yang:mac-address";
                    default "00:00:00:00:00:00";
                }
                leaf "FwallL2Fwd_DeviceInName" {
                    when "not (../FwallL2Fwd_DeviceIn != 'Other')";
                    type "string" {
                        pattern "[a-zA-Z0-9_.-]{0,16}";
                    }
                    default "";
                }
                leaf "FwallL2Fwd_DeviceOut" {
                    type "lbox_network_devices_phy";
                    must "not ((. = 'Radio' and (/config_data/device/DeviceHw/RR_DynHw_Primary_Radio != 'On')) or (. = 'ETH1' and (/config_data/device/DeviceHw/RR_DynHw_Port_Eth_Cnt <= 0)) or (. = 'ETH2' and (/config_data/device/DeviceHw/RR_DynHw_Port_Eth_Cnt <= 1)) or (. = 'ETH3' and (/config_data/device/DeviceHw/RR_DynHw_Port_Eth_Cnt <= 2)) or (. = 'ETH4' and (/config_data/device/DeviceHw/RR_DynHw_Port_Eth_Cnt <= 3)) or (. = 'ETH5' and (/config_data/device/DeviceHw/RR_DynHw_Port_Sfp != 'On')))";
                    default "All";
                }
                leaf "FwallL2Fwd_Arp_SrcIpMask" {
                    when "not ((../FwallL2Fwd_VlanEncap = 'On') or (../FwallL2Fwd_EtherType != 'LB_l2_protocol_V_ARP'))";
                    type "lim_ipv4_mask0";
                    default "0";
                }
                leaf "FwallL2Fwd_Arp_DstIpMask" {
                    when "not ((../FwallL2Fwd_VlanEncap = 'On') or (../FwallL2Fwd_EtherType != 'LB_l2_protocol_V_ARP'))";
                    type "lim_ipv4_mask0";
                    default "0";
                }
                leaf "FwallL2Fwd_DeviceOutName" {
                    when "not (../FwallL2Fwd_DeviceOut != 'Other')";
                    type "string" {
                        pattern "[a-zA-Z0-9_.-]{0,16}";
                    }
                    default "";
                }
                leaf "FwallL2Fwd_BridgeId" {
                    when "not (../FwallL2Fwd_BridgeFilter != 'On')";
                    type "lim_uint_16";
                    default "0";
                }
                leaf "FwallL2Fwd_TL_FrameCount" {
                    when "not (../FwallL2Fwd_TrafficLimit != 'On')";
                    type "lim_fwall_traffic_filter";
                    must ". <= ../FwallL2Fwd_TL_FrameBurst" {
                        error-message "valmsg_it_FwallL2Fwd_TL_FrameCount";
                    }
                    default "3";
                }
                leaf "FwallL2Fwd_TL_TimePeriod" {
                    when "not (../FwallL2Fwd_TrafficLimit != 'On')";
                    type "lbox_fwall_filter_limit_period";
                    default "LB_fwall_filter_limit_period_V_minute";
                }
                leaf "FwallL2Fwd_TL_FrameBurst" {
                    when "not (../FwallL2Fwd_TrafficLimit != 'On')";
                    type "lim_fwall_traffic_filter";
                    must ". >= ../FwallL2Fwd_TL_FrameCount" {
                        error-message "valmsg_it_FwallL2Fwd_TL_FrameBurst";
                    }
                    default "3";
                }
                leaf "FwallL2Fwd_Arp_OpCode" {
                    when "not ((../FwallL2Fwd_VlanEncap = 'On') or (../FwallL2Fwd_EtherType != 'LB_l2_protocol_V_ARP'))";
                    type "enumeration" {
                        enum "LB_FwallL2Fwd_Arp_OpCode_V_All" {
                            value "0";
                        }
                        enum "LB_FwallL2Fwd_Arp_OpCode_V_Request" {
                            value "1";
                        }
                        enum "LB_FwallL2Fwd_Arp_OpCode_V_Reply" {
                            value "2";
                        }
                    }
                    default "LB_FwallL2Fwd_Arp_OpCode_V_All";
                }
                leaf "FwallL2Fwd_Arp_SrcIp" {
                    when "not ((../FwallL2Fwd_VlanEncap = 'On') or (../FwallL2Fwd_EtherType != 'LB_l2_protocol_V_ARP'))";
                    type "inet:ipv4-address";
                    default "0.0.0.0";
                }
                leaf "FwallL2Fwd_Arp_DstIp" {
                    when "not ((../FwallL2Fwd_VlanEncap = 'On') or (../FwallL2Fwd_EtherType != 'LB_l2_protocol_V_ARP'))";
                    type "inet:ipv4-address";
                    default "0.0.0.0";
                }
                leaf "FwallL2Fwd_Ip_Protocol" {
                    when "not ((../FwallL2Fwd_VlanEncap = 'On') or (../FwallL2Fwd_EtherType != 'LB_l2_protocol_V_IPv4'))";
                    type "lbox_l3_protocol";
                    default "All";
                }
                leaf "FwallL2Fwd_Ip_SrcIpMask" {
                    when "not ((../FwallL2Fwd_VlanEncap = 'On') or (../FwallL2Fwd_EtherType != 'LB_l2_protocol_V_IPv4'))";
                    type "lim_ipv4_mask0";
                    default "0";
                }
                leaf "FwallL2Fwd_Ip_DstIpMask" {
                    when "not ((../FwallL2Fwd_VlanEncap = 'On') or (../FwallL2Fwd_EtherType != 'LB_l2_protocol_V_IPv4'))";
                    type "lim_ipv4_mask0";
                    default "0";
                }
                leaf "FwallL2Fwd_Ip_ProtocolNum" {
                    when "not ((../FwallL2Fwd_VlanEncap = 'On') or (../FwallL2Fwd_EtherType != 'LB_l2_protocol_V_IPv4') or (../FwallL2Fwd_Ip_Protocol != 'Other'))";
                    type "lim_uint_8_1toFF";
                    default "1";
                }
                leaf "FwallL2Fwd_Ip_SrcIp" {
                    when "not ((../FwallL2Fwd_VlanEncap = 'On') or (../FwallL2Fwd_EtherType != 'LB_l2_protocol_V_IPv4'))";
                    type "inet:ipv4-address";
                    default "0.0.0.0";
                }
                leaf "FwallL2Fwd_Ip_DstIp" {
                    when "not ((../FwallL2Fwd_VlanEncap = 'On') or (../FwallL2Fwd_EtherType != 'LB_l2_protocol_V_IPv4'))";
                    type "inet:ipv4-address";
                    default "0.0.0.0";
                }
                leaf "FwallL2Fwd_Ip_SrcPortStart" {
                    when "not ((../FwallL2Fwd_VlanEncap = 'On') or (../FwallL2Fwd_EtherType != 'LB_l2_protocol_V_IPv4') or (../FwallL2Fwd_Ip_Protocol != 'UDP' and ../FwallL2Fwd_Ip_Protocol != 'TCP'))";
                    type "lim_udp_port0";
                    must ". <= ../FwallL2Fwd_Ip_SrcPortEnd" {
                        error-message "valmsg_it_FwallL2Fwd_Ip_SrcPortStart";
                    }
                    default "0";
                }
                leaf "FwallL2Fwd_Ip_SrcPortEnd" {
                    when "not ((../FwallL2Fwd_VlanEncap = 'On') or (../FwallL2Fwd_EtherType != 'LB_l2_protocol_V_IPv4') or (../FwallL2Fwd_Ip_Protocol != 'UDP' and ../FwallL2Fwd_Ip_Protocol != 'TCP'))";
                    type "lim_udp_port0";
                    must ". >= ../FwallL2Fwd_Ip_SrcPortStart" {
                        error-message "valmsg_it_FwallL2Fwd_Ip_SrcPortEnd";
                    }
                    default "0";
                }
                leaf "FwallL2Fwd_Ip_DstPortStart" {
                    when "not ((../FwallL2Fwd_VlanEncap = 'On') or (../FwallL2Fwd_EtherType != 'LB_l2_protocol_V_IPv4') or (../FwallL2Fwd_Ip_Protocol != 'UDP' and ../FwallL2Fwd_Ip_Protocol != 'TCP'))";
                    type "lim_udp_port0";
                    must ". <= ../FwallL2Fwd_Ip_DstPortEnd" {
                        error-message "valmsg_it_FwallL2Fwd_Ip_DstPortStart";
                    }
                    default "0";
                }
                leaf "FwallL2Fwd_Ip_DstPortEnd" {
                    when "not ((../FwallL2Fwd_VlanEncap = 'On') or (../FwallL2Fwd_EtherType != 'LB_l2_protocol_V_IPv4') or (../FwallL2Fwd_Ip_Protocol != 'UDP' and ../FwallL2Fwd_Ip_Protocol != 'TCP'))";
                    type "lim_udp_port0";
                    must ". >= ../FwallL2Fwd_Ip_DstPortStart" {
                        error-message "valmsg_it_FwallL2Fwd_Ip_DstPortEnd";
                    }
                    default "0";
                }
                leaf "FwallL2Fwd_LogId" {
                    when "not ((/config_data/main/FirewallL2FwdLog/RR_FirewallL2FwdLog_En != 'On') or (../FwallL2Fwd_LogEn != 'On'))";
                    type "string" {
                        pattern "[a-zA-Z0-9_-]{0,12}";
                    }
                    default "";
                }
                leaf "FwallL2Fwd_LogEn" {
                    when "not (/config_data/main/FirewallL2FwdLog/RR_FirewallL2FwdLog_En != 'On')";
                    type "lbox_off_on";
                    default "Off";
                }
                leaf "FwallL2Fwd_LogSeverity" {
                    when "not ((/config_data/main/FirewallL2FwdLog/RR_FirewallL2FwdLog_En != 'On') or (../FwallL2Fwd_LogEn != 'On'))";
                    type "lbox_event_severity";
                    default "Notice";
                }
            }
            list "RR_S_TABLE_NatSnatRules" {
                when "not (/config_data/main/Networking/RR_NatMode != 'On')";
                key "ID";
                max-elements "256";
                ordered-by "user";
                leaf "ID" {
                    type "lim_uint_16";
                }
                leaf "NatSnat_ItActive" {
                    type "enumeration" {
                        enum "Off" {
                            value "0";
                        }
                        enum "On" {
                            value "1";
                        }
                    }
                    must "not ((. = 'On' and (((/config_data/main/Cellular/RR_CellMain_Enable != 'On') and (../NatSnat_DeviceOut = 'WWAN')) or ((/config_data/main/Cellular/RR_CellAux_Enable != 'On') and (/config_data/main/Wifi/RR_WifiExt_Enable != 'On') and (../NatSnat_DeviceOut = 'EXT')) or ((/config_data/main/ComPort_1/RR_ComPort_1_Protocol != 'PPP') and (/config_data/main/ComPort_2/RR_ComPort_2_Protocol != 'PPP') and (/config_data/main/ComPort_3/RR_ComPort_3_Protocol != 'PPP') and (../NatSnat_DeviceOut = 'All PPP')) or ((/config_data/main/Networking/RR_PppoeClient_Enable != 'On') and (../NatSnat_DeviceOut = 'PPPoE client')) or ((/config_data/main/VPN/RR_GreL3Enable != 'On') and (../NatSnat_DeviceOut = 'GRE L3')) or ((/config_data/main/VPN/RR_OpenVpnEnable != 'On') and (../NatSnat_DeviceOut = 'OpenVPN L3')) or ((/config_data/main/HotStdby/RR_HotStdby_Enable != 'On') and (../NatSnat_DeviceOut = 'HotStandby')) or ((/config_data/main/RadioInterface/RR_RadioIfMode != 'Router') and (../NatSnat_DeviceOut = 'Radio')))))";
                    default "On";
                }
                leaf "NatSnat_Protocol" {
                    type "lbox_l3_protocol";
                    default "All";
                }
                leaf "NatSnat_Note" {
                    type "string" {
                        pattern "[^\"`\\\\$;]{0,42}";
                    }
                    default "";
                }
                leaf "NatSnat_ProtocolNum" {
                    when "not (../NatSnat_Protocol != 'Other')";
                    type "lim_uint_8_1toFF";
                    default "1";
                }
                leaf "NatSnat_SrcIp" {
                    type "inet:ipv4-address";
                    default "0.0.0.0";
                }
                leaf "NatSnat_SrcIpMask" {
                    type "lim_ipv4_mask0";
                    default "0";
                }
                leaf "NatSnat_DstIpMask" {
                    type "lim_ipv4_mask0";
                    default "0";
                }
                leaf "NatSnat_DeviceOut" {
                    type "lbox_network_devices_log_M8";
                    must "not ((. = 'Radio' and (/config_data/device/DeviceHw/RR_DynHw_Primary_Radio != 'On')) or (. = 'WWAN' and (/config_data/device/DeviceHw/RR_DynHw_Primary_Cellular != 'On')) or (. = 'EXT' and ((/config_data/device/DeviceHw/RR_DynHw_Module_Cellular != 'On') and (/config_data/device/DeviceHw/RR_DynHw_Module_Wifi != 'On'))) or (. = 'HotStandby' and (/config_data/device/DeviceHw/RR_DynHw_HotStandby != 'On')))";
                    default "All";
                }
                leaf "NatSnat_SrcPortStart" {
                    when "not (../NatSnat_Protocol != 'UDP' and ../NatSnat_Protocol != 'TCP')";
                    type "lim_udp_port0";
                    must ". <= ../NatSnat_SrcPortEnd" {
                        error-message "valmsg_it_NatSnat_SrcPortStart";
                    }
                    default "0";
                }
                leaf "NatSnat_SrcPortEnd" {
                    when "not (../NatSnat_Protocol != 'UDP' and ../NatSnat_Protocol != 'TCP')";
                    type "lim_udp_port0";
                    must ". >= ../NatSnat_SrcPortStart" {
                        error-message "valmsg_it_NatSnat_SrcPortEnd";
                    }
                    default "0";
                }
                leaf "NatSnat_DstIp" {
                    type "inet:ipv4-address";
                    default "0.0.0.0";
                }
                leaf "NatSnat_DstPortStart" {
                    when "not (../NatSnat_Protocol != 'UDP' and ../NatSnat_Protocol != 'TCP')";
                    type "lim_udp_port0";
                    must ". <= ../NatSnat_DstPortEnd" {
                        error-message "valmsg_it_NatSnat_DstPortStart";
                    }
                    default "0";
                }
                leaf "NatSnat_DstPortEnd" {
                    when "not (../NatSnat_Protocol != 'UDP' and ../NatSnat_Protocol != 'TCP')";
                    type "lim_udp_port0";
                    must ". >= ../NatSnat_DstPortStart" {
                        error-message "valmsg_it_NatSnat_DstPortEnd";
                    }
                    default "0";
                }
                leaf "NatSnat_DeviceOutName" {
                    when "not (../NatSnat_DeviceOut != 'Other')";
                    type "string" {
                        pattern "[a-zA-Z0-9_.-]{0,16}";
                    }
                    default "";
                }
                leaf "NatSnat_RangeMapping" {
                    type "enumeration" {
                        enum "Off" {
                            value "0";
                        }
                        enum "IP address to IP address" {
                            value "1";
                        }
                    }
                    default "Off";
                }
                leaf "NatSnat_RewriteToIpMask" {
                    when "not (../NatSnat_RangeMapping != 'IP address to IP address')";
                    type "lim_ipv4_mask";
                    default "32";
                }
                leaf "NatSnat_RewriteToIp" {
                    type "inet:ipv4-address";
                    default "0.0.0.0";
                }
                leaf "NatSnat_RewriteToPort" {
                    when "not ((../NatSnat_Protocol != 'UDP' and ../NatSnat_Protocol != 'TCP') or (../NatSnat_RangeMapping = 'IP address to IP address'))";
                    type "lim_udp_port0";
                    default "0";
                }
                leaf "NatSnat_LogId" {
                    when "not ((/config_data/main/NatLog/RR_NatLog_En != 'On') or (../NatSnat_LogEn != 'On'))";
                    type "string" {
                        pattern "[a-zA-Z0-9_-]{0,12}";
                    }
                    default "";
                }
                leaf "NatSnat_LogEn" {
                    when "not (/config_data/main/NatLog/RR_NatLog_En != 'On')";
                    type "lbox_off_on";
                    default "Off";
                }
                leaf "NatSnat_LogSeverity" {
                    when "not ((/config_data/main/NatLog/RR_NatLog_En != 'On') or (../NatSnat_LogEn != 'On'))";
                    type "lbox_event_severity";
                    default "Notice";
                }
            }
            list "RR_S_TABLE_NatDnatRules" {
                when "not (/config_data/main/Networking/RR_NatMode != 'On')";
                key "ID";
                max-elements "256";
                ordered-by "user";
                leaf "ID" {
                    type "lim_uint_16";
                }
                leaf "NatDnat_ItActive" {
                    type "enumeration" {
                        enum "Off" {
                            value "0";
                        }
                        enum "On" {
                            value "1";
                        }
                    }
                    must "not ((. = 'On' and (((/config_data/main/Cellular/RR_CellMain_Enable != 'On') and (../NatDnat_DeviceIn = 'WWAN')) or ((/config_data/main/Cellular/RR_CellAux_Enable != 'On') and (/config_data/main/Wifi/RR_WifiExt_Enable != 'On') and (../NatDnat_DeviceIn = 'EXT')) or ((/config_data/main/ComPort_1/RR_ComPort_1_Protocol != 'PPP') and (/config_data/main/ComPort_2/RR_ComPort_2_Protocol != 'PPP') and (/config_data/main/ComPort_3/RR_ComPort_3_Protocol != 'PPP') and (../NatDnat_DeviceIn = 'All PPP')) or ((/config_data/main/Networking/RR_PppoeClient_Enable != 'On') and (../NatDnat_DeviceIn = 'PPPoE client')) or ((/config_data/main/VPN/RR_GreL3Enable != 'On') and (../NatDnat_DeviceIn = 'GRE L3')) or ((/config_data/main/VPN/RR_OpenVpnEnable != 'On') and (../NatDnat_DeviceIn = 'OpenVPN L3')) or ((/config_data/main/HotStdby/RR_HotStdby_Enable != 'On') and (../NatDnat_DeviceIn = 'HotStandby')) or ((/config_data/main/RadioInterface/RR_RadioIfMode != 'Router') and (../NatDnat_DeviceIn = 'Radio')))))";
                    default "On";
                }
                leaf "NatDnat_Protocol" {
                    type "lbox_l3_protocol";
                    default "All";
                }
                leaf "NatDnat_Note" {
                    type "string" {
                        pattern "[^\"`\\\\$;]{0,42}";
                    }
                    default "";
                }
                leaf "NatDnat_ProtocolNum" {
                    when "not (../NatDnat_Protocol != 'Other')";
                    type "lim_uint_8_1toFF";
                    default "1";
                }
                leaf "NatDnat_SrcIp" {
                    type "inet:ipv4-address";
                    default "0.0.0.0";
                }
                leaf "NatDnat_SrcIpMask" {
                    type "lim_ipv4_mask0";
                    default "0";
                }
                leaf "NatDnat_DstIpMask" {
                    type "lim_ipv4_mask0";
                    default "0";
                }
                leaf "NatDnat_DeviceIn" {
                    type "lbox_network_devices_log_M8";
                    must "not ((. = 'Radio' and (/config_data/device/DeviceHw/RR_DynHw_Primary_Radio != 'On')) or (. = 'WWAN' and (/config_data/device/DeviceHw/RR_DynHw_Primary_Cellular != 'On')) or (. = 'EXT' and ((/config_data/device/DeviceHw/RR_DynHw_Module_Cellular != 'On') and (/config_data/device/DeviceHw/RR_DynHw_Module_Wifi != 'On'))) or (. = 'HotStandby' and (/config_data/device/DeviceHw/RR_DynHw_HotStandby != 'On')))";
                    default "All";
                }
                leaf "NatDnat_SrcPortStart" {
                    when "not (../NatDnat_Protocol != 'UDP' and ../NatDnat_Protocol != 'TCP')";
                    type "lim_udp_port0";
                    must ". <= ../NatDnat_SrcPortEnd" {
                        error-message "valmsg_it_NatDnat_SrcPortStart";
                    }
                    default "0";
                }
                leaf "NatDnat_SrcPortEnd" {
                    when "not (../NatDnat_Protocol != 'UDP' and ../NatDnat_Protocol != 'TCP')";
                    type "lim_udp_port0";
                    must ". >= ../NatDnat_SrcPortStart" {
                        error-message "valmsg_it_NatDnat_SrcPortEnd";
                    }
                    default "0";
                }
                leaf "NatDnat_DstIp" {
                    type "inet:ipv4-address";
                    default "0.0.0.0";
                }
                leaf "NatDnat_DstPortStart" {
                    when "not (../NatDnat_Protocol != 'UDP' and ../NatDnat_Protocol != 'TCP')";
                    type "lim_udp_port0";
                    must ". <= ../NatDnat_DstPortEnd" {
                        error-message "valmsg_it_NatDnat_DstPortStart";
                    }
                    default "0";
                }
                leaf "NatDnat_DstPortEnd" {
                    when "not (../NatDnat_Protocol != 'UDP' and ../NatDnat_Protocol != 'TCP')";
                    type "lim_udp_port0";
                    must ". >= ../NatDnat_DstPortStart" {
                        error-message "valmsg_it_NatDnat_DstPortEnd";
                    }
                    default "0";
                }
                leaf "NatDnat_DeviceInName" {
                    when "not (../NatDnat_DeviceIn != 'Other')";
                    type "string" {
                        pattern "[a-zA-Z0-9_.-]{0,16}";
                    }
                    default "";
                }
                leaf "NatDnat_RangeMapping" {
                    type "enumeration" {
                        enum "Off" {
                            value "0";
                        }
                        enum "IP address to IP address" {
                            value "1";
                        }
                        enum "Port to IP address" {
                            value "2";
                        }
                    }
                    must "not ((. = 'Port to IP address' and ((../NatDnat_Protocol != 'UDP' and ../NatDnat_Protocol != 'TCP') or (../NatDnat_DstPortStart >= ../NatDnat_DstPortEnd))))";
                    default "Off";
                }
                leaf "NatDnat_RewriteToIpMask" {
                    when "not (../NatDnat_RangeMapping != 'IP address to IP address')";
                    type "lim_ipv4_mask";
                    default "32";
                }
                leaf "NatDnat_RewriteToIp" {
                    type "inet:ipv4-address";
                    default "0.0.0.0";
                }
                leaf "NatDnat_RewriteToPort" {
                    when "not ((../NatDnat_Protocol != 'UDP' and ../NatDnat_Protocol != 'TCP') or (../NatDnat_RangeMapping = 'IP address to IP address'))";
                    type "lim_udp_port0";
                    default "0";
                }
                leaf "NatDnat_LogId" {
                    when "not ((/config_data/main/NatLog/RR_NatLog_En != 'On') or (../NatDnat_LogEn != 'On'))";
                    type "string" {
                        pattern "[a-zA-Z0-9_-]{0,12}";
                    }
                    default "";
                }
                leaf "NatDnat_LogEn" {
                    when "not (/config_data/main/NatLog/RR_NatLog_En != 'On')";
                    type "lbox_off_on";
                    default "Off";
                }
                leaf "NatDnat_LogSeverity" {
                    when "not ((/config_data/main/NatLog/RR_NatLog_En != 'On') or (../NatDnat_LogEn != 'On'))";
                    type "lbox_event_severity";
                    default "Notice";
                }
            }
            list "RR_S_TABLE_QoSInterfaces" {
                when "not (/config_data/main/Networking/RR_QoSMode != 'On')";
                key "ID";
                max-elements "16";
                leaf "ID" {
                    type "lim_uint_16";
                }
                leaf "QoSIface_ItActive" {
                    type "lbox_off_on";
                    default "On";
                }
                leaf "QoSIface_Egr_Type" {
                    type "enumeration" {
                        enum "Strict_priority" {
                            value "0";
                        }
                        enum "Rate_limiting" {
                            value "1";
                        }
                    }
                    default "Strict_priority";
                }
                leaf "QoSIface_Egr_PrioFallback" {
                    when "not (../QoSIface_Egr_Type != 'Strict_priority')";
                    type "lbox_qos_priority";
                    default "8 (Lowest)";
                }
                leaf "QoSIface_Egr_HtbFallback" {
                    when "not (../QoSIface_Egr_Type != 'Rate_limiting')";
                    type "lbox_qos_flow_label";
                    default "Flow_H";
                }
                leaf "QoSIface_Egr_MaxRate_Unit" {
                    type "lbox_qos_rate_unit";
                    default "Mibps";
                }
                leaf "QoSIface_Note" {
                    type "string" {
                        pattern "[^\"`\\\\$;]{0,42}";
                    }
                    default "";
                }
                leaf "QoSIface_IfName" {
                    type "string" {
                        pattern "[a-zA-Z0-9_.-]{0,16}";
                    }
                    default "";
                }
                leaf "QoSIface_Egr_MaxRate_Val" {
                    type "lim_qos_rate_limit";
                    default "1";
                }
                leaf "QoSIface_TargetDelay" {
                    type "uint16" {
                        range "5..10000";
                    }
                    default "5";
                }
            }
            list "RR_S_TABLE_QoSEgrHtbFlows" {
                when "not (/config_data/main/Networking/RR_QoSMode != 'On')";
                key "ID";
                max-elements "128";
                leaf "ID" {
                    type "lim_uint_16";
                }
                leaf "ID_Parent" {
                    type "lim_uint_16";
                    default "0";
                }
                leaf "QoSEHFlow_ItActive" {
                    type "lbox_off_on";
                    default "On";
                }
                leaf "QoSEHFlow_Label" {
                    type "lbox_qos_flow_label";
                    default "Flow_A";
                }
                leaf "QoSEHFlow_Prio" {
                    type "enumeration" {
                        enum "1_Highest" {
                            value "0";
                        }
                        enum "2" {
                            value "1";
                        }
                        enum "3" {
                            value "2";
                        }
                        enum "4" {
                            value "3";
                        }
                        enum "5" {
                            value "4";
                        }
                        enum "6" {
                            value "5";
                        }
                        enum "7_Lowest" {
                            value "6";
                        }
                    }
                    default "1_Highest";
                }
                leaf "QoSEHFlow_MaxRate_Unit" {
                    type "lbox_qos_rate_unit";
                    default "kibps";
                }
                leaf "QoSEHFlow_GrntRate_Ena" {
                    type "lbox_off_on";
                    default "Off";
                }
                leaf "QoSEHFlow_Note" {
                    type "string" {
                        pattern "[^\"`\\\\$;]{0,42}";
                    }
                    default "";
                }
                leaf "QoSEHFlow_MaxRate_Val" {
                    type "lim_qos_rate_limit";
                    default "1";
                }
                leaf "QoSEHFlow_GrntRate_Val" {
                    when "not (../QoSEHFlow_GrntRate_Ena != 'On')";
                    type "lim_qos_rate_limit";
                    default "1";
                }
            }
            list "RR_S_TABLE_QoSEgrFilterRules" {
                when "not (/config_data/main/Networking/RR_QoSMode != 'On')";
                key "ID";
                max-elements "256";
                ordered-by "user";
                leaf "ID" {
                    type "lim_uint_16";
                }
                leaf "ID_Parent" {
                    type "lim_uint_16";
                    default "0";
                }
                leaf "QoSERule_ItActive" {
                    type "lbox_off_on";
                    default "On";
                }
                leaf "QoSERule_Protocol" {
                    type "lbox_l3_protocol";
                    default "All";
                }
                leaf "QoSERule_DS_Type" {
                    type "lbox_qos_ds_type";
                    default "Off";
                }
                leaf "QoSERule_VlanPrioSet" {
                    type "lbox_off_on";
                    default "Off";
                }
                leaf "QoSERule_SrcIpMask" {
                    type "lim_ipv4_mask0";
                    default "0";
                }
                leaf "QoSERule_SrcRUdpPort" {
                    when "not (../QoSERule_Protocol != 'UDP')";
                    type "lbox_udp_reserved_ports";
                    default "MANUAL";
                }
                leaf "QoSERule_DstIpMask" {
                    type "lim_ipv4_mask0";
                    default "0";
                }
                leaf "QoSERule_Note" {
                    type "string" {
                        pattern "[^\"`\\\\$;]{0,42}";
                    }
                    default "";
                }
                leaf "QoSERule_ProtocolNum" {
                    when "not (../QoSERule_Protocol != 'Other')";
                    type "lim_uint_8_1toFF";
                    default "1";
                }
                leaf "QoSERule_SrcIp" {
                    type "inet:ipv4-address";
                    default "0.0.0.0";
                }
                leaf "QoSERule_SrcPort" {
                    when "not ((../QoSERule_Protocol != 'UDP' and ../QoSERule_Protocol != 'TCP') or ((../QoSERule_Protocol = 'UDP') and (../QoSERule_SrcRUdpPort != 'MANUAL')))";
                    type "lim_udp_port0";
                    default "0";
                }
                leaf "QoSERule_DstIp" {
                    type "inet:ipv4-address";
                    default "0.0.0.0";
                }
                leaf "QoSERule_DstRUdpPort" {
                    when "not (../QoSERule_Protocol != 'UDP')";
                    type "lbox_udp_reserved_ports";
                    default "MANUAL";
                }
                leaf "QoSERule_DS_DSCP" {
                    when "not (../QoSERule_DS_Type != 'DSCP')";
                    type "lim_qos_dscp";
                    default "0";
                }
                leaf "QoSERule_DS_Precedence" {
                    when "not (../QoSERule_DS_Type != 'TOS_Precedence')";
                    type "lim_qos_tos_precedence";
                    default "0";
                }
                leaf "QoSERule_Target" {
                    type "lbox_qos_target";
                    default "Flow_A_Prio_1_Highest";
                }
                leaf "QoSERule_DstPort" {
                    when "not ((../QoSERule_Protocol != 'UDP' and ../QoSERule_Protocol != 'TCP') or ((../QoSERule_Protocol = 'UDP') and (../QoSERule_DstRUdpPort != 'MANUAL')))";
                    type "lim_udp_port0";
                    default "0";
                }
                leaf "QoSERule_VlanPrioVal" {
                    when "not (../QoSERule_VlanPrioSet != 'On')";
                    type "lim_qos_vlan_priority";
                    default "0";
                }
                leaf "QoSERule_SrcPortUseMask" {
                    when "not ((../QoSERule_Protocol != 'UDP' and ../QoSERule_Protocol != 'TCP') or ((../QoSERule_Protocol = 'UDP') and (../QoSERule_SrcRUdpPort != 'MANUAL')))";
                    type "lbox_off_on";
                    default "Off";
                }
                leaf "QoSERule_SrcPortMask" {
                    when "not ((../QoSERule_Protocol != 'UDP' and ../QoSERule_Protocol != 'TCP') or ((../QoSERule_Protocol = 'UDP') and (../QoSERule_SrcRUdpPort != 'MANUAL')) or (../QoSERule_SrcPortUseMask != 'On'))";
                    type "lim_l4_port_mask";
                    default "16";
                }
                leaf "QoSERule_DstPortUseMask" {
                    when "not ((../QoSERule_Protocol != 'UDP' and ../QoSERule_Protocol != 'TCP') or ((../QoSERule_Protocol = 'UDP') and (../QoSERule_DstRUdpPort != 'MANUAL')))";
                    type "lbox_off_on";
                    default "Off";
                }
                leaf "QoSERule_DstPortMask" {
                    when "not ((../QoSERule_Protocol != 'UDP' and ../QoSERule_Protocol != 'TCP') or ((../QoSERule_Protocol = 'UDP') and (../QoSERule_DstRUdpPort != 'MANUAL')) or (../QoSERule_DstPortUseMask != 'On'))";
                    type "lim_l4_port_mask";
                    default "16";
                }
            }
            list "RR_S_TABLE_DhcpServers" {
                when "not (/config_data/main/Networking/RR_DhcpServerEn != 'On')";
                key "ID";
                max-elements "16";
                leaf "ID" {
                    type "lim_uint_16";
                }
                leaf "DhcpSrv_ItActive" {
                    type "lbox_off_on";
                    default "On";
                }
                leaf "DhcpSrv_LeaseTime" {
                    type "uint16" {
                        range "2..10080";
                    }
                    default "60";
                }
                leaf "DhcpSrv_StaticOnly" {
                    type "lbox_off_on";
                    default "Off";
                }
                leaf "DhcpSrv_Note" {
                    type "string" {
                        pattern "[^\"`\\\\$;]{0,42}";
                    }
                    default "";
                }
                leaf "DhcpSrv_IpStart" {
                    type "inet:ipv4-address";
                    must "(round(16777216 * number(substring-before(., \".\")) + 65536 * number(substring-before(substring-after(., \".\"), \".\")) + 256 * number(substring-before(substring-after(substring-after(., \".\"), \".\"), \".\")) + number(substring-after(substring-after(substring-after(., \".\"), \".\"), \".\")))) <= (round(16777216 * number(substring-before(../DhcpSrv_IpEnd, \".\")) + 65536 * number(substring-before(substring-after(../DhcpSrv_IpEnd, \".\"), \".\")) + 256 * number(substring-before(substring-after(substring-after(../DhcpSrv_IpEnd, \".\"), \".\"), \".\")) + number(substring-after(substring-after(substring-after(../DhcpSrv_IpEnd, \".\"), \".\"), \".\"))))" {
                        error-message "valmsg_it_DhcpSrv_IpStart";
                    }
                    default "0.0.0.0";
                }
                leaf "DhcpSrv_IpEnd" {
                    type "inet:ipv4-address";
                    must "(round(16777216 * number(substring-before(., \".\")) + 65536 * number(substring-before(substring-after(., \".\"), \".\")) + 256 * number(substring-before(substring-after(substring-after(., \".\"), \".\"), \".\")) + number(substring-after(substring-after(substring-after(., \".\"), \".\"), \".\")))) >= (round(16777216 * number(substring-before(../DhcpSrv_IpStart, \".\")) + 65536 * number(substring-before(substring-after(../DhcpSrv_IpStart, \".\"), \".\")) + 256 * number(substring-before(substring-after(substring-after(../DhcpSrv_IpStart, \".\"), \".\"), \".\")) + number(substring-after(substring-after(substring-after(../DhcpSrv_IpStart, \".\"), \".\"), \".\"))))" {
                        error-message "valmsg_it_DhcpSrv_IpEnd";
                    }
                    default "0.0.0.0";
                }
                leaf "DhcpSrv_Gateway" {
                    type "lbox_dhcp_srv_announce";
                    default "LB_dhcp_srv_announce_V_Local";
                }
                leaf "DhcpSrv_Dns" {
                    type "enumeration" {
                        enum "LB_dhcp_srv_announce_V_Off" {
                            value "0";
                        }
                        enum "LB_dhcp_srv_announce_V_Local" {
                            value "1";
                        }
                        enum "LB_dhcp_srv_announce_V_Manual" {
                            value "2";
                        }
                    }
                    must "not ((. = 'LB_dhcp_srv_announce_V_Local' and (/config_data/main/Networking/RR_DnsForwardingEn != 'On')))";
                    default "LB_dhcp_srv_announce_V_Off";
                }
                leaf "DhcpSrv_Dns_UseSecondary" {
                    when "not (../DhcpSrv_Dns != 'LB_dhcp_srv_announce_V_Manual')";
                    type "lbox_off_on";
                    default "Off";
                }
                leaf "DhcpSrv_Ntp" {
                    type "lbox_dhcp_srv_announce";
                    default "LB_dhcp_srv_announce_V_Off";
                }
                leaf "DhcpSrv_Gateway_Addr" {
                    when "not (../DhcpSrv_Gateway != 'LB_dhcp_srv_announce_V_Manual')";
                    type "inet:ipv4-address";
                    default "0.0.0.0";
                }
                leaf "DhcpSrv_Dns_PrimaryAddr" {
                    when "not (../DhcpSrv_Dns != 'LB_dhcp_srv_announce_V_Manual')";
                    type "inet:ipv4-address";
                    default "0.0.0.0";
                }
                leaf "DhcpSrv_Dns_SecondaryAddr" {
                    when "not ((../DhcpSrv_Dns != 'LB_dhcp_srv_announce_V_Manual') or (../DhcpSrv_Dns_UseSecondary != 'On'))";
                    type "inet:ipv4-address";
                    default "0.0.0.0";
                }
                leaf "DhcpSrv_Ntp_Addr" {
                    when "not (../DhcpSrv_Ntp != 'LB_dhcp_srv_announce_V_Manual')";
                    type "inet:ipv4-address";
                    default "0.0.0.0";
                }
            }
            list "RR_S_TABLE_DhcpStaticLeases" {
                when "not (/config_data/main/Networking/RR_DhcpServerEn != 'On')";
                key "ID";
                max-elements "1024";
                leaf "ID" {
                    type "lim_uint_16";
                }
                leaf "ID_Parent" {
                    type "lim_uint_16";
                    default "0";
                }
                leaf "DhcpStLease_ItActive" {
                    type "lbox_off_on";
                    default "On";
                }
                leaf "DhcpStLease_Note" {
                    type "string" {
                        pattern "[^\"`\\\\$;]{0,42}";
                    }
                    default "";
                }
                leaf "DhcpStLease_MacAddr" {
                    type "yang:mac-address";
                    default "00:00:00:00:00:00";
                }
                leaf "DhcpStLease_IpAddr" {
                    type "inet:ipv4-address";
                    default "0.0.0.0";
                }
            }
            list "RR_S_TABLE_DnsServers" {
                when "not ((/config_data/main/Networking/RR_DnsForwardingEn != 'On') or (/config_data/main/DnsForwarding/RR_DnsFwd_ServerList != 'LB_DnsFwd_ServerList_V_Static'))";
                key "ID";
                max-elements "32";
                ordered-by "user";
                leaf "ID" {
                    type "lim_uint_16";
                }
                leaf "DnsSrv_ItActive" {
                    type "lbox_off_on";
                    default "On";
                }
                leaf "DnsSrv_Note" {
                    type "string" {
                        pattern "[^\"`\\\\$;]{0,42}";
                    }
                    default "";
                }
                leaf "DnsSrv_IpAddr" {
                    type "inet:ipv4-address";
                    default "0.0.0.0";
                }
                leaf "DnsSrv_Port" {
                    type "lim_udp_port";
                    default "53";
                }
                leaf "DnsSrv_Domain" {
                    type "string" {
                        pattern "[a-zA-Z0-9.*-]{0,128}";
                    }
                    default "";
                }
            }
            list "RR_S_TABLE_DnsBlockNames" {
                when "not (/config_data/main/Networking/RR_DnsForwardingEn != 'On')";
                key "ID";
                max-elements "128";
                leaf "ID" {
                    type "lim_uint_16";
                }
                leaf "DnsBlock_ItActive" {
                    type "lbox_off_on";
                    default "On";
                }
                leaf "DnsBlock_Note" {
                    type "string" {
                        pattern "[^\"`\\\\$;]{0,42}";
                    }
                    default "";
                }
                leaf "DnsBlock_Domain" {
                    type "string" {
                        pattern "[a-zA-Z0-9.*-]{1,128}";
                    }
                    default "example.com";
                }
            }
            list "RR_S_TABLE_DnsSecTrustAnchors" {
                when "not ((/config_data/main/Networking/RR_DnsForwardingEn != 'On') or (/config_data/main/DnsForwarding/RR_DnsFwd_Cache != 'On') or (/config_data/main/DnsForwarding/RR_DnsFwd_DnsSec != 'On'))";
                key "ID";
                max-elements "8";
                leaf "ID" {
                    type "lim_uint_16";
                }
                leaf "DnsSecTA_ItActive" {
                    type "lbox_off_on";
                    default "On";
                }
                leaf "DnsSecTA_Note" {
                    type "string" {
                        pattern "[^\"`\\\\$;]{0,42}";
                    }
                    default "";
                }
                leaf "DnsSecTA_KeyTag" {
                    type "lim_uint_16";
                    default "0";
                }
                leaf "DnsSecTA_Algorithm" {
                    type "lim_uint_8";
                    default "0";
                }
                leaf "DnsSecTA_DigestType" {
                    type "lim_uint_8";
                    default "0";
                }
                leaf "DnsSecTA_Digest" {
                    type "string" {
                        pattern "[0-9a-fA-F]{0,256}";
                    }
                    default "";
                }
            }
            list "RR_S_TABLE_RoutingRules" {
                key "ID";
                max-elements "512";
                leaf "ID" {
                    type "lim_uint_16";
                }
                leaf "Routing_DstAddr" {
                    type "inet:ipv4-address";
                    default "0.0.0.0";
                }
                leaf "Routing_ItActive" {
                    type "enumeration" {
                        enum "Off" {
                            value "0";
                        }
                        enum "On" {
                            value "1";
                        }
                    }
                    must "not ((. = 'On' and (((../Routing_Mode = 'WWAN (MAIN)') and (/config_data/main/Cellular/RR_CellMain_Enable != 'On')) or ((../Routing_Mode = 'WWAN (EXT)') and (/config_data/main/Cellular/RR_CellAux_Enable != 'On') and ((/config_data/main/Wifi/RR_WifiExt_Enable != 'On') or (/config_data/main/WifiExt/RR_WifiExt_OperationType != 'LB_wifi_operation_type_Client'))) or ((../Routing_Mode = 'PPP 1') and ((/config_data/main/ComPort_1/RR_ComPort_1_ENA != 'On') or (/config_data/main/ComPort_1/RR_ComPort_1_Protocol != 'PPP'))) or ((../Routing_Mode = 'PPP 2') and ((/config_data/main/ComPort_2/RR_ComPort_2_ENA != 'On') or (/config_data/main/ComPort_2/RR_ComPort_2_Protocol != 'PPP'))) or ((../Routing_Mode = 'PPP 3') and ((/config_data/main/ComPort_3/RR_ComPort_3_ENA != 'On') or (/config_data/main/ComPort_3/RR_ComPort_3_Protocol != 'PPP'))) or ((../Routing_Mode = 'LB_Routing_Mode_Link_manager') and (/config_data/main/Networking/RR_LinkManagerEn != 'On')) or ((../Routing_Mode = 'LB_Routing_Mode_Pppoe_client') and (/config_data/main/Networking/RR_PppoeClient_Enable != 'On')))))";
                    default "On";
                }
                leaf "Routing_DstMask" {
                    type "lim_ipv4_mask0";
                    default "32";
                }
                leaf "Routing_Mode" {
                    type "enumeration" {
                        enum "Static" {
                            value "0";
                        }
                        enum "WWAN (MAIN)" {
                            value "2";
                        }
                        enum "WWAN (EXT)" {
                            value "1";
                        }
                        enum "PPP 1" {
                            value "3";
                        }
                        enum "PPP 2" {
                            value "4";
                        }
                        enum "PPP 3" {
                            value "5";
                        }
                        enum "LB_Routing_Mode_Link_manager" {
                            value "6";
                        }
                        enum "LB_Routing_Mode_Pppoe_client" {
                            value "7";
                        }
                    }
                    must "not ((. = 'WWAN (MAIN)' and (/config_data/device/DeviceHw/RR_DynHw_Primary_Cellular != 'On')) or (. = 'WWAN (EXT)' and ((/config_data/device/DeviceHw/RR_DynHw_Module_Cellular != 'On') and (/config_data/device/DeviceHw/RR_DynHw_Module_Wifi != 'On'))) or (. = 'PPP 1' and (/config_data/device/DeviceHw/RR_DynHw_Port_Com1 != 'On')) or (. = 'PPP 2' and (/config_data/device/DeviceHw/RR_DynHw_Port_Com2 != 'On')) or (. = 'PPP 3' and (/config_data/device/DeviceHw/RR_DynHw_Port_Com3 != 'On')))";
                    default "Static";
                }
                leaf "Routing_Persistent" {
                    when "not (../Routing_Mode = 'Static')";
                    type "lbox_off_on";
                    default "Off";
                }
                leaf "Routing_NHopAddr" {
                    when "not (../Routing_Mode != 'Static')";
                    type "inet:ipv4-address";
                    default "0.0.0.0";
                }
                leaf "Routing_LocalUseSrcAddr" {
                    type "inet:ipv4-address";
                    default "0.0.0.0";
                }
                leaf "Routing_Note" {
                    type "string" {
                        pattern "[^\"`\\\\$;]{0,42}";
                    }
                    default "";
                }
                leaf "Routing_Metric" {
                    type "lim_routing_metric";
                    default "0";
                }
            }
            list "RR_S_TABLE_OspfAreas" {
                when "not ((/config_data/main/Networking/RR_AdvancedDynRouting != 'On') or (/config_data/main/AdvDynamicRouting/RR_ADR_OspfEn != 'On'))";
                key "ID";
                max-elements "32";
                description "Cnf. group for OSPF: row of table OspfAreas";
                leaf "ID" {
                    type "lim_uint_16";
                }
                leaf "OspfArea_ItActive" {
                    type "lbox_off_on";
                    default "On";
                }
                leaf "OspfArea_StubArea" {
                    type "enumeration" {
                        enum "Off" {
                            value "0";
                        }
                        enum "On" {
                            value "1";
                        }
                    }
                    must "not ((. = 'On' and (../OspfArea_Id = '0.0.0.0')))";
                    default "Off";
                }
                leaf "OspfArea_StubDefaultGw" {
                    when "not (../OspfArea_StubArea != 'On')";
                    type "lbox_off_on";
                    default "On";
                }
                leaf "OspfArea_Note" {
                    type "string" {
                        pattern "[^\"`\\\\$;]{0,42}";
                    }
                    default "";
                }
                leaf "OspfArea_Id" {
                    type "inet:ipv4-address";
                    default "0.0.0.0";
                }
            }
            list "RR_S_TABLE_OspfInterfaces" {
                when "not ((/config_data/main/Networking/RR_AdvancedDynRouting != 'On') or (/config_data/main/AdvDynamicRouting/RR_ADR_OspfEn != 'On'))";
                key "ID";
                max-elements "128";
                leaf "ID" {
                    type "lim_uint_16";
                }
                leaf "ID_Parent" {
                    type "lim_uint_16";
                    default "0";
                }
                leaf "OspfIface_ItActive" {
                    type "lbox_off_on";
                    default "On";
                }
                leaf "OspfIface_TtlSecurity" {
                    when "not (../OspfIface_Type = 'Stub')";
                    type "lbox_off_on";
                    default "Off";
                }
                leaf "OspfIface_UseBroadcast" {
                    when "not (../OspfIface_Type != 'Broadcast' and ../OspfIface_Type != 'Point2Point')";
                    type "lbox_off_on";
                    default "Off";
                }
                leaf "OspfIface_HelloInterval" {
                    when "not (../OspfIface_Type = 'Stub')";
                    type "uint16" {
                        range "1..3600";
                    }
                    default "10";
                }
                leaf "OspfIface_Note" {
                    type "string" {
                        pattern "[^\"`\\\\$;]{0,42}";
                    }
                    default "";
                }
                leaf "Ospf_IfName" {
                    type "string" {
                        pattern "[a-zA-Z0-9_.-]{0,16}";
                    }
                    default "";
                }
                leaf "OspfIface_NetAddr" {
                    type "inet:ipv4-address";
                    default "0.0.0.0";
                }
                leaf "OspfIface_NetMask" {
                    type "lim_ipv4_mask0";
                    default "0";
                }
                leaf "OspfIface_Type" {
                    type "enumeration" {
                        enum "Broadcast" {
                            value "0";
                        }
                        enum "Point2Point" {
                            value "1";
                        }
                        enum "Point2Multipoint" {
                            value "2";
                        }
                        enum "NBMA" {
                            value "3";
                        }
                        enum "Stub" {
                            value "4";
                        }
                    }
                    default "Broadcast";
                }
                leaf "OspfIface_DeadCount" {
                    when "not (../OspfIface_Type = 'Stub')";
                    type "uint8" {
                        range "2..64";
                    }
                    default "4";
                }
                leaf "OspfIface_Cost" {
                    type "lim_adr_metric";
                    default "10";
                }
                leaf "OspfIface_Authentication" {
                    when "not (../OspfIface_Type = 'Stub')";
                    type "enumeration" {
                        enum "None" {
                            value "0";
                        }
                        enum "Keyed MD5 (OSPFv2)" {
                            value "1";
                        }
                        enum "HMAC SHA256" {
                            value "2";
                        }
                        enum "HMAC SHA384" {
                            value "3";
                        }
                        enum "HMAC SHA512" {
                            value "4";
                        }
                    }
                    default "None";
                }
                leaf "OspfIface_PollInterval" {
                    when "not (../OspfIface_Type != 'NBMA')";
                    type "uint16" {
                        range "1..3600";
                    }
                    default "20";
                }
                leaf "OspfIface_RetransTime" {
                    when "not (../OspfIface_Type = 'Stub')";
                    type "uint16" {
                        range "1..3600";
                    }
                    default "5";
                }
                leaf "OspfIface_DRPriority" {
                    when "not (../OspfIface_Type != 'Broadcast' and ../OspfIface_Type != 'NBMA')";
                    type "lim_uint_8";
                    default "1";
                }
                leaf "OspfIface_Password" {
                    when "not (../OspfIface_Authentication = 'None')";
                    type "string" {
                        pattern "[^\"`\\\\$;]{0,128}";
                    }
                    default "";
                }
            }
            list "RR_S_TABLE_OspfIfaceNeighbors" {
                when "not ((/config_data/main/Networking/RR_AdvancedDynRouting != 'On') or (/config_data/main/AdvDynamicRouting/RR_ADR_OspfEn != 'On'))";
                key "ID";
                max-elements "512";
                leaf "ID" {
                    type "lim_uint_16";
                }
                leaf "ID_Parent" {
                    type "lim_uint_16";
                    default "0";
                }
                leaf "OspfIfNeigh_ItActive" {
                    type "lbox_off_on";
                    default "On";
                }
                leaf "OspfIfNeigh_Note" {
                    type "string" {
                        pattern "[^\"`\\\\$;]{0,42}";
                    }
                    default "";
                }
                leaf "OspfIfNeigh_IpAddr" {
                    type "inet:ipv4-address";
                    default "0.0.0.0";
                }
            }
            list "RR_S_TABLE_OspfNetworks" {
                when "not ((/config_data/main/Networking/RR_AdvancedDynRouting != 'On') or (/config_data/main/AdvDynamicRouting/RR_ADR_OspfEn != 'On'))";
                key "ID";
                max-elements "256";
                leaf "ID" {
                    type "lim_uint_16";
                }
                leaf "ID_Parent" {
                    type "lim_uint_16";
                    default "0";
                }
                leaf "OspfNet_ItActive" {
                    type "lbox_off_on";
                    default "On";
                }
                leaf "OspfNet_NetMask" {
                    type "lim_ipv4_mask0";
                    default "32";
                }
                leaf "OspfNet_Action" {
                    type "enumeration" {
                        enum "Aggregate" {
                            value "0";
                        }
                        enum "Hide" {
                            value "1";
                        }
                    }
                    default "Aggregate";
                }
                leaf "OspfNet_Note" {
                    type "string" {
                        pattern "[^\"`\\\\$;]{0,42}";
                    }
                    default "";
                }
                leaf "OspfNet_NetAddr" {
                    type "inet:ipv4-address";
                    default "0.0.0.0";
                }
            }
            list "RR_S_TABLE_OspfStaticRules" {
                when "not ((/config_data/main/Networking/RR_AdvancedDynRouting != 'On') or (/config_data/main/AdvDynamicRouting/RR_ADR_OspfEn != 'On'))";
                key "ID";
                max-elements "256";
                leaf "ID" {
                    type "lim_uint_16";
                }
                leaf "OspfStRule_ItActive" {
                    type "lbox_off_on";
                    default "On";
                }
                leaf "OspfStRule_DstMask" {
                    type "lim_ipv4_mask0";
                    default "0";
                }
                leaf "OspfStRule_MetricType" {
                    type "lbox_ospf_metric_type";
                    default "Type 1";
                }
                leaf "OspfStRule_Note" {
                    type "string" {
                        pattern "[^\"`\\\\$;]{0,42}";
                    }
                    default "";
                }
                leaf "OspfStRule_DstAddr" {
                    type "inet:ipv4-address";
                    default "0.0.0.0";
                }
                leaf "OspfStRule_Metric" {
                    type "lim_adr_metric";
                    default "1000";
                }
                leaf "OspfStRule_Tag" {
                    type "lim_uint_32";
                    default "0";
                }
            }
            list "RR_S_TABLE_OspfImFilterRules" {
                when "not ((/config_data/main/Networking/RR_AdvancedDynRouting != 'On') or (/config_data/main/AdvDynamicRouting/RR_ADR_OspfEn != 'On'))";
                key "ID";
                max-elements "256";
                ordered-by "user";
                leaf "ID" {
                    type "lim_uint_16";
                }
                leaf "OspfImFRule_ItActive" {
                    type "lbox_off_on";
                    default "On";
                }
                leaf "OspfImFRule_FilterNet" {
                    type "lbox_adr_filter_match";
                    default "Off";
                }
                leaf "OspfImFRule_FNetMask" {
                    when "not (../OspfImFRule_FilterNet = 'Off')";
                    type "lim_ipv4_mask0";
                    default "0";
                }
                leaf "OspfImFRule_FNetMaskFrom" {
                    when "not (../OspfImFRule_FilterNet = 'Off')";
                    type "lim_ipv4_mask0";
                    must ". <= ../OspfImFRule_FNetMaskTo" {
                        error-message "valmsg_it_OspfImFRule_FNetMaskFrom";
                    }
                    default "0";
                }
                leaf "OspfImFRule_Note" {
                    type "string" {
                        pattern "[^\"`\\\\$;]{0,42}";
                    }
                    default "";
                }
                leaf "OspfImFRule_FNetAddr" {
                    when "not (../OspfImFRule_FilterNet = 'Off')";
                    type "inet:ipv4-address";
                    default "0.0.0.0";
                }
                leaf "OspfImFRule_FNetMaskTo" {
                    when "not (../OspfImFRule_FilterNet = 'Off')";
                    type "lim_ipv4_mask0";
                    must ". >= ../OspfImFRule_FNetMaskFrom" {
                        error-message "valmsg_it_OspfImFRule_FNetMaskTo";
                    }
                    default "32";
                }
                leaf "OspfImFRule_FilterSource" {
                    type "lbox_adr_filter_match";
                    default "Off";
                }
                leaf "OspfImFRule_FSource" {
                    when "not (../OspfImFRule_FilterSource = 'Off')";
                    type "lbox_ospf_source";
                    default "External type 1";
                }
                leaf "OspfImFRule_FilterTag" {
                    type "lbox_adr_filter_match";
                    default "Off";
                }
                leaf "OspfImFRule_Action" {
                    type "lbox_adr_filter_action";
                    default "Accept";
                }
                leaf "OspfImFRule_SetPreference" {
                    when "not (../OspfImFRule_Action = 'Reject')";
                    type "lbox_off_on";
                    default "Off";
                }
                leaf "OspfImFRule_FTag" {
                    when "not (../OspfImFRule_FilterTag = 'Off')";
                    type "lim_uint_32";
                    default "0";
                }
                leaf "OspfImFRule_Preference" {
                    when "not ((../OspfImFRule_Action = 'Reject') or (../OspfImFRule_SetPreference != 'On'))";
                    type "lim_adr_preference";
                    default "200";
                }
                leaf "OspfImFRule_LocalUseSrcAddr" {
                    when "not (../OspfImFRule_Action = 'Reject')";
                    type "inet:ipv4-address";
                    default "0.0.0.0";
                }
            }
            list "RR_S_TABLE_OspfExFilterRules" {
                when "not ((/config_data/main/Networking/RR_AdvancedDynRouting != 'On') or (/config_data/main/AdvDynamicRouting/RR_ADR_OspfEn != 'On'))";
                key "ID";
                max-elements "256";
                ordered-by "user";
                leaf "ID" {
                    type "lim_uint_16";
                }
                leaf "OspfExFRule_ItActive" {
                    type "lbox_off_on";
                    default "On";
                }
                leaf "OspfExFRule_FilterNet" {
                    type "lbox_adr_filter_match";
                    default "Off";
                }
                leaf "OspfExFRule_FNetMask" {
                    when "not (../OspfExFRule_FilterNet = 'Off')";
                    type "lim_ipv4_mask0";
                    default "0";
                }
                leaf "OspfExFRule_FNetMaskFrom" {
                    when "not (../OspfExFRule_FilterNet = 'Off')";
                    type "lim_ipv4_mask0";
                    must ". <= ../OspfExFRule_FNetMaskTo" {
                        error-message "valmsg_it_OspfExFRule_FNetMaskFrom";
                    }
                    default "0";
                }
                leaf "OspfExFRule_SetMetricType" {
                    when "not (../OspfExFRule_Action = 'Reject')";
                    type "lbox_ospf_metric_type";
                    default "Type 2";
                }
                leaf "OspfExFRule_Note" {
                    type "string" {
                        pattern "[^\"`\\\\$;]{0,42}";
                    }
                    default "";
                }
                leaf "OspfExFRule_FNetAddr" {
                    when "not (../OspfExFRule_FilterNet = 'Off')";
                    type "inet:ipv4-address";
                    default "0.0.0.0";
                }
                leaf "OspfExFRule_FNetMaskTo" {
                    when "not (../OspfExFRule_FilterNet = 'Off')";
                    type "lim_ipv4_mask0";
                    must ". >= ../OspfExFRule_FNetMaskFrom" {
                        error-message "valmsg_it_OspfExFRule_FNetMaskTo";
                    }
                    default "32";
                }
                leaf "OspfExFRule_FilterProtocol" {
                    type "lbox_adr_filter_match";
                    default "Off";
                }
                leaf "OspfExFRule_FProtocol" {
                    when "not (../OspfExFRule_FilterProtocol = 'Off')";
                    type "enumeration" {
                        enum "System" {
                            value "0";
                        }
                        enum "BGP" {
                            value "1";
                        }
                        enum "BGP external" {
                            value "2";
                        }
                        enum "BGP internal" {
                            value "3";
                        }
                        enum "Babel" {
                            value "4";
                        }
                    }
                    must "not ((. = 'BGP' and (/config_data/main/AdvDynamicRouting/RR_ADR_BgpEn != 'On')) or (. = 'BGP external' and (/config_data/main/AdvDynamicRouting/RR_ADR_BgpEn != 'On')) or (. = 'BGP internal' and (/config_data/main/AdvDynamicRouting/RR_ADR_BgpEn != 'On')) or (. = 'Babel' and (/config_data/main/AdvDynamicRouting/RR_ADR_BabelEn != 'On')))";
                    default "System";
                }
                leaf "OspfExFRule_FilterBgpPath" {
                    when "not ((../OspfExFRule_FilterProtocol != 'Match') or (../OspfExFRule_FProtocol != 'BGP' and ../OspfExFRule_FProtocol != 'BGP internal'))";
                    type "lbox_adr_filter_bgppath_simple";
                    default "Off";
                }
                leaf "OspfExFRule_Action" {
                    type "lbox_adr_filter_action";
                    default "Accept";
                }
                leaf "OspfExFRule_SetTag" {
                    when "not (../OspfExFRule_Action = 'Reject')";
                    type "lbox_off_on";
                    default "Off";
                }
                leaf "OspfExFRule_Metric" {
                    when "not (../OspfExFRule_Action = 'Reject')";
                    type "lim_adr_metric";
                    default "10000";
                }
                leaf "OspfExFRule_Tag" {
                    when "not ((../OspfExFRule_Action = 'Reject') or (../OspfExFRule_SetTag != 'On'))";
                    type "lim_uint_32";
                    default "0";
                }
                leaf "OspfExFRule_SetMetricFromOtherProt" {
                    when "not (../OspfExFRule_Action = 'Reject')";
                    type "enumeration" {
                        enum "Off" {
                            value "0";
                        }
                        enum "BGP MED" {
                            value "1";
                        }
                        enum "Babel metric" {
                            value "2";
                        }
                    }
                    must "not ((. = 'BGP MED' and (/config_data/main/AdvDynamicRouting/RR_ADR_BgpEn != 'On')) or (. = 'Babel metric' and (/config_data/main/AdvDynamicRouting/RR_ADR_BabelEn != 'On')))";
                    default "Off";
                }
            }
            list "RR_S_TABLE_BgpNeighbors" {
                when "not ((/config_data/main/Networking/RR_AdvancedDynRouting != 'On') or (/config_data/main/AdvDynamicRouting/RR_ADR_BgpEn != 'On'))";
                key "ID";
                max-elements "256";
                leaf "ID" {
                    type "lim_uint_16";
                }
                leaf "BgpNeigh_ItActive" {
                    type "lbox_off_on";
                    default "On";
                }
                leaf "BgpNeigh_Type" {
                    type "enumeration" {
                        enum "Internal" {
                            value "0";
                        }
                        enum "External" {
                            value "1";
                        }
                    }
                    default "External";
                }
                leaf "BgpNeigh_HoldInterval" {
                    type "uint16" {
                        range "3..10800";
                    }
                    default "240";
                }
                leaf "BgpNeigh_Note" {
                    type "string" {
                        pattern "[^\"`\\\\$;]{0,42}";
                    }
                    default "";
                }
                leaf "BgpNeigh_NeighborAS" {
                    when "not (../BgpNeigh_Type != 'External')";
                    type "lim_uint_32";
                    default "65000";
                }
                leaf "BgpNeigh_NeighAddr" {
                    type "inet:ipv4-address";
                    default "0.0.0.0";
                }
                leaf "BgpNeigh_LocalAddr" {
                    type "inet:ipv4-address";
                    default "0.0.0.0";
                }
                leaf "BgpNeigh_Connection" {
                    type "enumeration" {
                        enum "Direct" {
                            value "0";
                        }
                        enum "Multihop" {
                            value "1";
                        }
                    }
                    default "Direct";
                }
                leaf "BgpNeigh_Md5Authentication" {
                    type "lbox_off_on";
                    default "Off";
                }
                leaf "BgpNeigh_Passive" {
                    type "lbox_off_on";
                    default "Off";
                }
                leaf "BgpNeigh_KeepInterval" {
                    type "uint16" {
                        range "1..3600";
                    }
                    default "80";
                }
                leaf "BgpNeigh_ConnRetryInterval" {
                    type "uint16" {
                        range "1..3600";
                    }
                    default "120";
                }
                leaf "BgpNeigh_TtlSecurity" {
                    type "lbox_off_on";
                    default "Off";
                }
                leaf "BgpNeigh_RRClient" {
                    when "not ((/config_data/main/Bgp/RR_Bgp_RouteReflector != 'On') or (../BgpNeigh_Type != 'Internal'))";
                    type "lbox_off_on";
                    default "Off";
                }
                leaf "BgpNeigh_SetCost" {
                    when "not (../BgpNeigh_Connection != 'Direct')";
                    type "lbox_off_on";
                    default "Off";
                }
                leaf "BgpNeigh_ExpHops" {
                    when "not ((../BgpNeigh_Connection != 'Multihop') or (../BgpNeigh_TtlSecurity != 'On'))";
                    type "uint8" {
                        range "2..32";
                    }
                    default "2";
                }
                leaf "BgpNeigh_SetNHopSelf" {
                    type "enumeration" {
                        enum "Off" {
                            value "0";
                        }
                        enum "Always" {
                            value "1";
                        }
                        enum "Internal" {
                            value "2";
                        }
                        enum "External" {
                            value "3";
                        }
                    }
                    default "Off";
                }
                leaf "BgpNeigh_Cost" {
                    when "not ((../BgpNeigh_Connection != 'Direct') or (../BgpNeigh_SetCost != 'On'))";
                    type "uint32" {
                        range "1..4294967295";
                    }
                    default "10";
                }
                leaf "BgpNeigh_Password" {
                    when "not (../BgpNeigh_Md5Authentication != 'On')";
                    type "string" {
                        pattern "[^\"`\\\\$;]{0,80}";
                    }
                    default "";
                }
            }
            list "RR_S_TABLE_BgpStaticRules" {
                when "not ((/config_data/main/Networking/RR_AdvancedDynRouting != 'On') or (/config_data/main/AdvDynamicRouting/RR_ADR_BgpEn != 'On'))";
                key "ID";
                max-elements "256";
                leaf "ID" {
                    type "lim_uint_16";
                }
                leaf "BgpStRule_ItActive" {
                    type "lbox_off_on";
                    default "On";
                }
                leaf "BgpStRule_DstMask" {
                    type "lim_ipv4_mask0";
                    default "32";
                }
                leaf "BgpStRule_Note" {
                    type "string" {
                        pattern "[^\"`\\\\$;]{0,42}";
                    }
                    default "";
                }
                leaf "BgpStRule_DstAddr" {
                    type "inet:ipv4-address";
                    default "0.0.0.0";
                }
            }
            list "RR_S_TABLE_BgpImIgpFilterRules" {
                when "not ((/config_data/main/Networking/RR_AdvancedDynRouting != 'On') or (/config_data/main/AdvDynamicRouting/RR_ADR_BgpEn != 'On'))";
                key "ID";
                max-elements "256";
                ordered-by "user";
                leaf "ID" {
                    type "lim_uint_16";
                }
                leaf "BgpImIgpFRule_ItActive" {
                    type "lbox_off_on";
                    default "On";
                }
                leaf "BgpImIgpFRule_FilterNet" {
                    type "lbox_adr_filter_match";
                    default "Off";
                }
                leaf "BgpImIgpFRule_FNetMask" {
                    when "not (../BgpImIgpFRule_FilterNet = 'Off')";
                    type "lim_ipv4_mask0";
                    default "0";
                }
                leaf "BgpImIgpFRule_FNetMaskFrom" {
                    when "not (../BgpImIgpFRule_FilterNet = 'Off')";
                    type "lim_ipv4_mask0";
                    must ". <= ../BgpImIgpFRule_FNetMaskTo" {
                        error-message "valmsg_it_BgpImIgpFRule_FNetMaskFrom";
                    }
                    default "0";
                }
                leaf "BgpImIgpFRule_Note" {
                    type "string" {
                        pattern "[^\"`\\\\$;]{0,42}";
                    }
                    default "";
                }
                leaf "BgpImIgpFRule_FNetAddr" {
                    when "not (../BgpImIgpFRule_FilterNet = 'Off')";
                    type "inet:ipv4-address";
                    default "0.0.0.0";
                }
                leaf "BgpImIgpFRule_FNetMaskTo" {
                    when "not (../BgpImIgpFRule_FilterNet = 'Off')";
                    type "lim_ipv4_mask0";
                    must ". >= ../BgpImIgpFRule_FNetMaskFrom" {
                        error-message "valmsg_it_BgpImIgpFRule_FNetMaskTo";
                    }
                    default "32";
                }
                leaf "BgpImIgpFRule_FilterSource" {
                    type "enumeration" {
                        enum "Off" {
                            value "0";
                        }
                        enum "Internal" {
                            value "1";
                        }
                        enum "External" {
                            value "2";
                        }
                    }
                    default "Off";
                }
                leaf "BgpImIgpFRule_FilterBgpPath" {
                    type "lbox_adr_filter_bgppath_full";
                    default "Off";
                }
                leaf "BgpImIgpFRule_FPathPosition" {
                    when "not (../BgpImIgpFRule_FilterBgpPath != 'Contain' and ../BgpImIgpFRule_FilterBgpPath != 'Not contain')";
                    type "lbox_adr_filter_bgppath_pos";
                    default "Any";
                }
                leaf "BgpImIgpFRule_Action" {
                    type "lbox_adr_filter_action";
                    default "Accept";
                }
                leaf "BgpImIgpFRule_SetPreference" {
                    when "not (../BgpImIgpFRule_Action = 'Reject')";
                    type "lbox_off_on";
                    default "Off";
                }
                leaf "BgpImIgpFRule_FPathAS" {
                    when "not (../BgpImIgpFRule_FilterBgpPath != 'Contain' and ../BgpImIgpFRule_FilterBgpPath != 'Not contain')";
                    type "lim_uint_32";
                    default "65000";
                }
                leaf "BgpImIgpFRule_Preference" {
                    when "not ((../BgpImIgpFRule_Action = 'Reject') or (../BgpImIgpFRule_SetPreference != 'On'))";
                    type "lim_adr_preference";
                    default "100";
                }
                leaf "BgpImIgpFRule_LocalUseSrcAddr" {
                    when "not (../BgpImIgpFRule_Action = 'Reject')";
                    type "inet:ipv4-address";
                    default "0.0.0.0";
                }
            }
            list "RR_S_TABLE_BgpExIgpFilterRules" {
                when "not ((/config_data/main/Networking/RR_AdvancedDynRouting != 'On') or (/config_data/main/AdvDynamicRouting/RR_ADR_BgpEn != 'On'))";
                key "ID";
                max-elements "256";
                ordered-by "user";
                leaf "ID" {
                    type "lim_uint_16";
                }
                leaf "BgpExIgpFRule_ItActive" {
                    type "lbox_off_on";
                    default "On";
                }
                leaf "BgpExIgpFRule_FilterNet" {
                    type "lbox_adr_filter_match";
                    default "Off";
                }
                leaf "BgpExIgpFRule_FNetMask" {
                    when "not (../BgpExIgpFRule_FilterNet = 'Off')";
                    type "lim_ipv4_mask0";
                    default "0";
                }
                leaf "BgpExIgpFRule_FNetMaskFrom" {
                    when "not (../BgpExIgpFRule_FilterNet = 'Off')";
                    type "lim_ipv4_mask0";
                    must ". <= ../BgpExIgpFRule_FNetMaskTo" {
                        error-message "valmsg_it_BgpExIgpFRule_FNetMaskFrom";
                    }
                    default "0";
                }
                leaf "BgpExIgpFRule_Note" {
                    type "string" {
                        pattern "[^\"`\\\\$;]{0,42}";
                    }
                    default "";
                }
                leaf "BgpExIgpFRule_FNetAddr" {
                    when "not (../BgpExIgpFRule_FilterNet = 'Off')";
                    type "inet:ipv4-address";
                    default "0.0.0.0";
                }
                leaf "BgpExIgpFRule_FNetMaskTo" {
                    when "not (../BgpExIgpFRule_FilterNet = 'Off')";
                    type "lim_ipv4_mask0";
                    must ". >= ../BgpExIgpFRule_FNetMaskFrom" {
                        error-message "valmsg_it_BgpExIgpFRule_FNetMaskTo";
                    }
                    default "32";
                }
                leaf "BgpExIgpFRule_FilterProtocol" {
                    type "lbox_adr_filter_match";
                    default "Off";
                }
                leaf "BgpExIgpFRule_FProtocol" {
                    when "not (../BgpExIgpFRule_FilterProtocol = 'Off')";
                    type "enumeration" {
                        enum "System" {
                            value "0";
                        }
                        enum "OSPF" {
                            value "1";
                        }
                        enum "Babel" {
                            value "2";
                        }
                    }
                    must "not ((. = 'OSPF' and (/config_data/main/AdvDynamicRouting/RR_ADR_OspfEn != 'On')) or (. = 'Babel' and (/config_data/main/AdvDynamicRouting/RR_ADR_BabelEn != 'On')))";
                    default "System";
                }
                leaf "BgpExIgpFRule_FilterOspfSource" {
                    when "not ((../BgpExIgpFRule_FilterProtocol != 'Match') or (../BgpExIgpFRule_FProtocol != 'OSPF'))";
                    type "lbox_adr_filter_match";
                    default "Off";
                }
                leaf "BgpExIgpFRule_FOspfSource" {
                    when "not ((../BgpExIgpFRule_FilterProtocol != 'Match') or (../BgpExIgpFRule_FProtocol != 'OSPF') or (../BgpExIgpFRule_FilterOspfSource = 'Off'))";
                    type "lbox_ospf_source";
                    default "External type 2";
                }
                leaf "BgpExIgpFRule_FilterOspfTag" {
                    when "not ((../BgpExIgpFRule_FilterProtocol != 'Match') or (../BgpExIgpFRule_FProtocol != 'OSPF'))";
                    type "lbox_adr_filter_match";
                    default "Off";
                }
                leaf "BgpExIgpFRule_FOspfTag" {
                    when "not ((../BgpExIgpFRule_FilterProtocol != 'Match') or (../BgpExIgpFRule_FProtocol != 'OSPF') or (../BgpExIgpFRule_FilterOspfTag = 'Off'))";
                    type "lim_uint_32";
                    default "0";
                }
                leaf "BgpExIgpFRule_Action" {
                    type "lbox_adr_filter_action";
                    default "Accept";
                }
            }
            list "RR_S_TABLE_BgpImOutFilterRules" {
                when "not ((/config_data/main/Networking/RR_AdvancedDynRouting != 'On') or (/config_data/main/AdvDynamicRouting/RR_ADR_BgpEn != 'On'))";
                key "ID";
                max-elements "256";
                ordered-by "user";
                leaf "ID" {
                    type "lim_uint_16";
                }
                leaf "BgpImOutFRule_ItActive" {
                    type "lbox_off_on";
                    default "On";
                }
                leaf "BgpImOutFRule_FilterBgpPath" {
                    type "lbox_adr_filter_bgppath_full";
                    default "Off";
                }
                leaf "BgpImOutFRule_FNetMask" {
                    when "not (../BgpImOutFRule_FilterNet = 'Off')";
                    type "lim_ipv4_mask0";
                    default "0";
                }
                leaf "BgpImOutFRule_FNetMaskFrom" {
                    when "not (../BgpImOutFRule_FilterNet = 'Off')";
                    type "lim_ipv4_mask0";
                    must ". <= ../BgpImOutFRule_FNetMaskTo" {
                        error-message "valmsg_it_BgpImOutFRule_FNetMaskFrom";
                    }
                    default "0";
                }
                leaf "BgpImOutFRule_Note" {
                    type "string" {
                        pattern "[^\"`\\\\$;]{0,42}";
                    }
                    default "";
                }
                leaf "BgpImOutFRule_FNetAddr" {
                    when "not (../BgpImOutFRule_FilterNet = 'Off')";
                    type "inet:ipv4-address";
                    default "0.0.0.0";
                }
                leaf "BgpImOutFRule_FilterNet" {
                    type "lbox_adr_filter_match";
                    default "Off";
                }
                leaf "BgpImOutFRule_FNetMaskTo" {
                    when "not (../BgpImOutFRule_FilterNet = 'Off')";
                    type "lim_ipv4_mask0";
                    must ". >= ../BgpImOutFRule_FNetMaskFrom" {
                        error-message "valmsg_it_BgpImOutFRule_FNetMaskTo";
                    }
                    default "32";
                }
                leaf "BgpImOutFRule_FPathPosition" {
                    when "not (../BgpImOutFRule_FilterBgpPath != 'Contain' and ../BgpImOutFRule_FilterBgpPath != 'Not contain')";
                    type "lbox_adr_filter_bgppath_pos";
                    default "Any";
                }
                leaf "BgpImOutFRule_Action" {
                    type "lbox_adr_filter_action";
                    default "Accept";
                }
                leaf "BgpImOutFRule_PrependLocAS" {
                    when "not (../BgpImOutFRule_Action = 'Reject')";
                    type "uint8" {
                        range "0..8";
                    }
                    default "0";
                }
                leaf "BgpImOutFRule_FPathAS" {
                    when "not (../BgpImOutFRule_FilterBgpPath != 'Contain' and ../BgpImOutFRule_FilterBgpPath != 'Not contain')";
                    type "lim_uint_32";
                    default "65000";
                }
            }
            list "RR_S_TABLE_BgpExOutFilterRules" {
                when "not ((/config_data/main/Networking/RR_AdvancedDynRouting != 'On') or (/config_data/main/AdvDynamicRouting/RR_ADR_BgpEn != 'On'))";
                key "ID";
                max-elements "256";
                ordered-by "user";
                leaf "ID" {
                    type "lim_uint_16";
                }
                leaf "BgpExOutFRule_ItActive" {
                    type "lbox_off_on";
                    default "On";
                }
                leaf "BgpExOutFRule_FProtocol" {
                    when "not (../BgpExOutFRule_FilterProtocol = 'Off')";
                    type "enumeration" {
                        enum "System" {
                            value "0";
                        }
                        enum "OSPF" {
                            value "1";
                        }
                        enum "BGP" {
                            value "2";
                        }
                        enum "BGP external" {
                            value "3";
                        }
                        enum "BGP internal" {
                            value "4";
                        }
                        enum "Babel" {
                            value "5";
                        }
                    }
                    must "not ((. = 'OSPF' and (/config_data/main/AdvDynamicRouting/RR_ADR_OspfEn != 'On')) or (. = 'Babel' and (/config_data/main/AdvDynamicRouting/RR_ADR_BabelEn != 'On')))";
                    default "System";
                }
                leaf "BgpExOutFRule_FNetMask" {
                    when "not (../BgpExOutFRule_FilterNet = 'Off')";
                    type "lim_ipv4_mask0";
                    default "0";
                }
                leaf "BgpExOutFRule_FNetMaskFrom" {
                    when "not (../BgpExOutFRule_FilterNet = 'Off')";
                    type "lim_ipv4_mask0";
                    must ". <= ../BgpExOutFRule_FNetMaskTo" {
                        error-message "valmsg_it_BgpExOutFRule_FNetMaskFrom";
                    }
                    default "0";
                }
                leaf "BgpExOutFRule_Note" {
                    type "string" {
                        pattern "[^\"`\\\\$;]{0,42}";
                    }
                    default "";
                }
                leaf "BgpExOutFRule_FilterNet" {
                    type "lbox_adr_filter_match";
                    default "Off";
                }
                leaf "BgpExOutFRule_FNetMaskTo" {
                    when "not (../BgpExOutFRule_FilterNet = 'Off')";
                    type "lim_ipv4_mask0";
                    must ". >= ../BgpExOutFRule_FNetMaskFrom" {
                        error-message "valmsg_it_BgpExOutFRule_FNetMaskTo";
                    }
                    default "32";
                }
                leaf "BgpExOutFRule_FilterProtocol" {
                    type "lbox_adr_filter_match";
                    default "Off";
                }
                leaf "BgpExOutFRule_FilterOspfTag" {
                    when "not ((../BgpExOutFRule_FilterProtocol != 'Match') or (../BgpExOutFRule_FProtocol != 'OSPF'))";
                    type "lbox_adr_filter_match";
                    default "Off";
                }
                leaf "BgpExOutFRule_FilterBgpPath" {
                    when "not ((../BgpExOutFRule_FilterProtocol != 'Match') or (../BgpExOutFRule_FProtocol != 'BGP' and ../BgpExOutFRule_FProtocol != 'BGP internal' and ../BgpExOutFRule_FProtocol != 'BGP external'))";
                    type "lbox_adr_filter_bgppath_full";
                    default "Off";
                }
                leaf "BgpExOutFRule_FNetAddr" {
                    when "not (../BgpExOutFRule_FilterNet = 'Off')";
                    type "inet:ipv4-address";
                    default "0.0.0.0";
                }
                leaf "BgpExOutFRule_FOspfTag" {
                    when "not ((../BgpExOutFRule_FilterProtocol != 'Match') or (../BgpExOutFRule_FProtocol != 'OSPF') or (../BgpExOutFRule_FilterOspfTag = 'Off'))";
                    type "lim_uint_32";
                    default "0";
                }
                leaf "BgpExOutFRule_FPathPosition" {
                    when "not ((../BgpExOutFRule_FilterProtocol != 'Match') or (../BgpExOutFRule_FProtocol != 'BGP' and ../BgpExOutFRule_FProtocol != 'BGP internal' and ../BgpExOutFRule_FProtocol != 'BGP external') or (../BgpExOutFRule_FilterBgpPath != 'Contain' and ../BgpExOutFRule_FilterBgpPath != 'Not contain'))";
                    type "lbox_adr_filter_bgppath_pos";
                    default "Any";
                }
                leaf "BgpExOutFRule_Action" {
                    type "lbox_adr_filter_action";
                    default "Accept";
                }
                leaf "BgpExOutFRule_FPathAS" {
                    when "not ((../BgpExOutFRule_FilterProtocol != 'Match') or (../BgpExOutFRule_FProtocol != 'BGP' and ../BgpExOutFRule_FProtocol != 'BGP internal' and ../BgpExOutFRule_FProtocol != 'BGP external') or (../BgpExOutFRule_FilterBgpPath != 'Contain' and ../BgpExOutFRule_FilterBgpPath != 'Not contain'))";
                    type "lim_uint_32";
                    default "65000";
                }
            }
            list "RR_S_TABLE_BabelInterfaces" {
                when "not ((/config_data/main/Networking/RR_AdvancedDynRouting != 'On') or (/config_data/main/AdvDynamicRouting/RR_ADR_BabelEn != 'On'))";
                key "ID";
                max-elements "64";
                leaf "ID" {
                    type "lim_uint_16";
                }
                leaf "BabelIface_ItActive" {
                    type "lbox_off_on";
                    default "On";
                }
                leaf "BabelIface_Type" {
                    type "enumeration" {
                        enum "Wired" {
                            value "0";
                        }
                        enum "Wireless" {
                            value "1";
                        }
                    }
                    default "Wireless";
                }
                leaf "BabelIface_HelloLimit" {
                    when "not (../BabelIface_Type != 'Wired')";
                    type "uint8" {
                        range "1..16";
                    }
                    default "12";
                }
                leaf "BabelIface_UpdateIntervalMult" {
                    type "uint8" {
                        range "2..30";
                    }
                    default "4";
                }
                leaf "BabelIface_AuthAlg" {
                    when "not (../BabelIface_Authentication = 'BabelIface_Authentication__None')";
                    type "enumeration" {
                        enum "HMAC SHA256" {
                            value "1";
                        }
                        enum "HMAC SHA384" {
                            value "2";
                        }
                        enum "HMAC SHA512" {
                            value "3";
                        }
                        enum "BLAKE2s-128" {
                            value "4";
                        }
                        enum "BLAKE2s-256" {
                            value "5";
                        }
                        enum "BLAKE2b-256" {
                            value "6";
                        }
                        enum "BLAKE2b-512" {
                            value "7";
                        }
                    }
                    default "HMAC SHA256";
                }
                leaf "BabelIface_Authentication" {
                    type "enumeration" {
                        enum "BabelIface_Authentication__None" {
                            value "0";
                        }
                        enum "BabelIface_Authentication__Full" {
                            value "1";
                        }
                        enum "BabelIface_Authentication__Only_sign" {
                            value "2";
                        }
                    }
                    default "BabelIface_Authentication__None";
                }
                leaf "BabelIface_Note" {
                    type "string" {
                        pattern "[^\"`\\\\$;]{0,42}";
                    }
                    default "";
                }
                leaf "BabelIface_IfName" {
                    type "string" {
                        pattern "[a-zA-Z0-9_.-]{0,16}";
                    }
                    default "";
                }
                leaf "BabelIface_RxCost" {
                    type "lim_adr_babel_metric";
                    default "128";
                }
                leaf "BabelIface_HelloInterval" {
                    type "decimal64" {
                        fraction-digits "1";
                        range "0.1..327.0";
                    }
                    default "4.0";
                }
                leaf "BabelIface_AdvertisedNextHop" {
                    type "inet:ipv4-address";
                    default "0.0.0.0";
                }
                leaf "BabelIface_Password" {
                    when "not (../BabelIface_Authentication = 'BabelIface_Authentication__None')";
                    type "string" {
                        pattern "[^\"`\\\\$;]{0,128}";
                    }
                    default "";
                }
            }
            list "RR_S_TABLE_BabelStaticRules" {
                when "not ((/config_data/main/Networking/RR_AdvancedDynRouting != 'On') or (/config_data/main/AdvDynamicRouting/RR_ADR_BabelEn != 'On'))";
                key "ID";
                max-elements "256";
                description "Cnf. group for Babel: row of table BabelStaticRules";
                leaf "ID" {
                    type "lim_uint_16";
                }
                leaf "BabelStRule_ItActive" {
                    type "lbox_off_on";
                    default "On";
                }
                leaf "BabelStRule_DstMask" {
                    type "lim_ipv4_mask0";
                    default "0";
                }
                leaf "BabelStRule_Note" {
                    type "string" {
                        pattern "[^\"`\\\\$;]{0,42}";
                    }
                    default "";
                }
                leaf "BabelStRule_DstAddr" {
                    type "inet:ipv4-address";
                    default "0.0.0.0";
                }
                leaf "BabelStRule_Metric" {
                    type "lim_adr_babel_metric0";
                    default "0";
                }
            }
            list "RR_S_TABLE_BabelImFilterRules" {
                when "not ((/config_data/main/Networking/RR_AdvancedDynRouting != 'On') or (/config_data/main/AdvDynamicRouting/RR_ADR_BabelEn != 'On'))";
                key "ID";
                max-elements "256";
                ordered-by "user";
                description "Cnf. group for Babel: row of table BabelImFilterRules";
                leaf "ID" {
                    type "lim_uint_16";
                }
                leaf "BabelImFRule_ItActive" {
                    type "lbox_off_on";
                    default "On";
                }
                leaf "BabelImFRule_FilterNet" {
                    type "lbox_adr_filter_match";
                    default "Off";
                }
                leaf "BabelImFRule_FNetMask" {
                    when "not (../BabelImFRule_FilterNet = 'Off')";
                    type "lim_ipv4_mask0";
                    default "0";
                }
                leaf "BabelImFRule_FNetMaskFrom" {
                    when "not (../BabelImFRule_FilterNet = 'Off')";
                    type "lim_ipv4_mask0";
                    must ". <= ../BabelImFRule_FNetMaskTo" {
                        error-message "valmsg_it_BabelImFRule_FNetMaskFrom";
                    }
                    default "0";
                }
                leaf "BabelImFRule_SetPreference" {
                    when "not (../BabelImFRule_Action = 'Reject')";
                    type "lbox_off_on";
                    default "Off";
                }
                leaf "BabelImFRule_Note" {
                    type "string" {
                        pattern "[^\"`\\\\$;]{0,42}";
                    }
                    default "";
                }
                leaf "BabelImFRule_FNetAddr" {
                    when "not (../BabelImFRule_FilterNet = 'Off')";
                    type "inet:ipv4-address";
                    default "0.0.0.0";
                }
                leaf "BabelImFRule_FNetMaskTo" {
                    when "not (../BabelImFRule_FilterNet = 'Off')";
                    type "lim_ipv4_mask0";
                    must ". >= ../BabelImFRule_FNetMaskFrom" {
                        error-message "valmsg_it_BabelImFRule_FNetMaskTo";
                    }
                    default "32";
                }
                leaf "BabelImFRule_Action" {
                    type "lbox_adr_filter_action";
                    default "Accept";
                }
                leaf "BabelImFRule_Preference" {
                    when "not ((../BabelImFRule_Action = 'Reject') or (../BabelImFRule_SetPreference != 'On'))";
                    type "lim_adr_preference";
                    default "210";
                }
                leaf "BabelImFRule_LocalUseSrcAddr" {
                    when "not (../BabelImFRule_Action = 'Reject')";
                    type "inet:ipv4-address";
                    default "0.0.0.0";
                }
            }
            list "RR_S_TABLE_BabelExFilterRules" {
                when "not ((/config_data/main/Networking/RR_AdvancedDynRouting != 'On') or (/config_data/main/AdvDynamicRouting/RR_ADR_BabelEn != 'On'))";
                key "ID";
                max-elements "256";
                ordered-by "user";
                description "Cnf. group for Babel: row of table BabelExFilterRules";
                leaf "ID" {
                    type "lim_uint_16";
                }
                leaf "BabelExFRule_ItActive" {
                    type "lbox_off_on";
                    default "On";
                }
                leaf "BabelExFRule_FilterNet" {
                    type "lbox_adr_filter_match";
                    default "Off";
                }
                leaf "BabelExFRule_FNetMask" {
                    when "not (../BabelExFRule_FilterNet = 'Off')";
                    type "lim_ipv4_mask0";
                    default "0";
                }
                leaf "BabelExFRule_FNetMaskFrom" {
                    when "not (../BabelExFRule_FilterNet = 'Off')";
                    type "lim_ipv4_mask0";
                    must ". <= ../BabelExFRule_FNetMaskTo" {
                        error-message "valmsg_it_BabelExFRule_FNetMaskFrom";
                    }
                    default "0";
                }
                leaf "BabelExFRule_Note" {
                    type "string" {
                        pattern "[^\"`\\\\$;]{0,42}";
                    }
                    default "";
                }
                leaf "BabelExFRule_FNetAddr" {
                    when "not (../BabelExFRule_FilterNet = 'Off')";
                    type "inet:ipv4-address";
                    default "0.0.0.0";
                }
                leaf "BabelExFRule_FNetMaskTo" {
                    when "not (../BabelExFRule_FilterNet = 'Off')";
                    type "lim_ipv4_mask0";
                    must ". >= ../BabelExFRule_FNetMaskFrom" {
                        error-message "valmsg_it_BabelExFRule_FNetMaskTo";
                    }
                    default "32";
                }
                leaf "BabelExFRule_FilterProtocol" {
                    type "lbox_adr_filter_match";
                    default "Off";
                }
                leaf "BabelExFRule_FProtocol" {
                    when "not (../BabelExFRule_FilterProtocol = 'Off')";
                    type "enumeration" {
                        enum "System" {
                            value "0";
                        }
                        enum "BGP" {
                            value "1";
                        }
                        enum "BGP external" {
                            value "2";
                        }
                        enum "BGP internal" {
                            value "3";
                        }
                        enum "OSPF" {
                            value "4";
                        }
                    }
                    must "not ((. = 'BGP' and (/config_data/main/AdvDynamicRouting/RR_ADR_BgpEn != 'On')) or (. = 'BGP external' and (/config_data/main/AdvDynamicRouting/RR_ADR_BgpEn != 'On')) or (. = 'BGP internal' and (/config_data/main/AdvDynamicRouting/RR_ADR_BgpEn != 'On')) or (. = 'OSPF' and (/config_data/main/AdvDynamicRouting/RR_ADR_OspfEn != 'On')))";
                    default "System";
                }
                leaf "BabelExFRule_FilterBgpPath" {
                    when "not ((../BabelExFRule_FilterProtocol != 'Match') or (../BabelExFRule_FProtocol != 'BGP' and ../BabelExFRule_FProtocol != 'BGP internal'))";
                    type "lbox_adr_filter_bgppath_simple";
                    default "Off";
                }
                leaf "BabelExFRule_SetMetricFromOtherProt" {
                    when "not (../BabelExFRule_Action = 'Reject')";
                    type "enumeration" {
                        enum "Off" {
                            value "0";
                        }
                        enum "BGP MED" {
                            value "1";
                        }
                        enum "OSPF metric 1" {
                            value "2";
                        }
                        enum "OSPF metric 2" {
                            value "3";
                        }
                        enum "OSPF metric sum" {
                            value "4";
                        }
                    }
                    must "not ((. = 'BGP MED' and (/config_data/main/AdvDynamicRouting/RR_ADR_BgpEn != 'On')) or (. = 'OSPF metric 1' and (/config_data/main/AdvDynamicRouting/RR_ADR_OspfEn != 'On')) or (. = 'OSPF metric 2' and (/config_data/main/AdvDynamicRouting/RR_ADR_OspfEn != 'On')) or (. = 'OSPF metric sum' and (/config_data/main/AdvDynamicRouting/RR_ADR_OspfEn != 'On')))";
                    default "Off";
                }
                leaf "BabelExFRule_FilterOspfSource" {
                    when "not ((../BabelExFRule_FilterProtocol != 'Match') or (../BabelExFRule_FProtocol != 'OSPF'))";
                    type "lbox_adr_filter_match";
                    default "Off";
                }
                leaf "BabelExFRule_FOspfSource" {
                    when "not ((../BabelExFRule_FilterProtocol != 'Match') or (../BabelExFRule_FProtocol != 'OSPF') or (../BabelExFRule_FilterOspfSource = 'Off'))";
                    type "lbox_ospf_source";
                    default "External type 2";
                }
                leaf "BabelExFRule_FilterOspfTag" {
                    when "not ((../BabelExFRule_FilterProtocol != 'Match') or (../BabelExFRule_FProtocol != 'OSPF'))";
                    type "lbox_adr_filter_match";
                    default "Off";
                }
                leaf "BabelExFRule_Action" {
                    type "lbox_adr_filter_action";
                    default "Accept";
                }
                leaf "BabelExFRule_FOspfTag" {
                    when "not ((../BabelExFRule_FilterProtocol != 'Match') or (../BabelExFRule_FProtocol != 'OSPF') or (../BabelExFRule_FilterOspfTag = 'Off'))";
                    type "lim_uint_32";
                    default "0";
                }
                leaf "BabelExFRule_Metric" {
                    when "not (../BabelExFRule_Action = 'Reject')";
                    type "lim_adr_babel_metric0";
                    default "0";
                }
            }
            list "RR_S_TABLE_BabelRelFilterRules" {
                when "not ((/config_data/main/Networking/RR_AdvancedDynRouting != 'On') or (/config_data/main/AdvDynamicRouting/RR_ADR_BabelEn != 'On'))";
                key "ID";
                max-elements "256";
                ordered-by "user";
                description "Cnf. group for Babel: row of table BabelRelFilterRules";
                leaf "ID" {
                    type "lim_uint_16";
                }
                leaf "BabelRelFRule_ItActive" {
                    type "lbox_off_on";
                    default "On";
                }
                leaf "BabelRelFRule_FilterNet" {
                    type "lbox_adr_filter_match";
                    default "Off";
                }
                leaf "BabelRelFRule_FNetMask" {
                    when "not (../BabelRelFRule_FilterNet = 'Off')";
                    type "lim_ipv4_mask0";
                    default "0";
                }
                leaf "BabelRelFRule_FNetMaskFrom" {
                    when "not (../BabelRelFRule_FilterNet = 'Off')";
                    type "lim_ipv4_mask0";
                    must ". <= ../BabelRelFRule_FNetMaskTo" {
                        error-message "valmsg_it_BabelRelFRule_FNetMaskFrom";
                    }
                    default "0";
                }
                leaf "BabelRelFRule_Note" {
                    type "string" {
                        pattern "[^\"`\\\\$;]{0,42}";
                    }
                    default "";
                }
                leaf "BabelRelFRule_FNetAddr" {
                    when "not (../BabelRelFRule_FilterNet = 'Off')";
                    type "inet:ipv4-address";
                    default "0.0.0.0";
                }
                leaf "BabelRelFRule_FNetMaskTo" {
                    when "not (../BabelRelFRule_FilterNet = 'Off')";
                    type "lim_ipv4_mask0";
                    must ". >= ../BabelRelFRule_FNetMaskFrom" {
                        error-message "valmsg_it_BabelRelFRule_FNetMaskTo";
                    }
                    default "32";
                }
                leaf "BabelRelFRule_FilterMetric" {
                    type "lbox_adr_filter_metric_cmp";
                    default "Off";
                }
                leaf "BabelRelFRule_Action" {
                    type "lbox_adr_filter_action";
                    default "Accept";
                }
                leaf "BabelRelFRule_IncreaseMetric" {
                    when "not (../BabelRelFRule_Action = 'Reject')";
                    type "lbox_off_on";
                    default "Off";
                }
                leaf "BabelRelFRule_FMetricValue" {
                    when "not (../BabelRelFRule_FilterMetric = 'Off')";
                    type "lim_adr_babel_metric0";
                    default "0";
                }
                leaf "BabelRelFRule_AddedMetric" {
                    when "not ((../BabelRelFRule_Action = 'Reject') or (../BabelRelFRule_IncreaseMetric != 'On'))";
                    type "lim_adr_babel_metric";
                    default "1";
                }
            }
            list "RR_S_TABLE_LinkMngLinks" {
                when "not (/config_data/main/Networking/RR_LinkManagerEn != 'On')";
                key "ID";
                max-elements "16";
                ordered-by "user";
                leaf "ID" {
                    type "lim_uint_16";
                }
                leaf "LinkMngLink_ItActive" {
                    type "enumeration" {
                        enum "Off" {
                            value "0";
                        }
                        enum "On" {
                            value "1";
                        }
                    }
                    must "not ((. = 'On' and (((/config_data/main/Cellular/RR_CellMain_Enable != 'On') and (../LinkMngLink_Type = 'LB_LinkMngLink_Type_WWAN_MAIN')) or ((/config_data/main/Cellular/RR_CellAux_Enable != 'On') and (/config_data/main/Wifi/RR_WifiExt_Enable != 'On') and (../LinkMngLink_Type = 'LB_LinkMngLink_Type_WWAN_EXT')) or (((/config_data/main/ComPort_1/RR_ComPort_1_ENA != 'On') or (/config_data/main/ComPort_1/RR_ComPort_1_Protocol != 'PPP')) and (../LinkMngLink_Type = 'LB_LinkMngLink_Type_Ppp_1')) or (((/config_data/main/ComPort_2/RR_ComPort_2_ENA != 'On') or (/config_data/main/ComPort_2/RR_ComPort_2_Protocol != 'PPP')) and (../LinkMngLink_Type = 'LB_LinkMngLink_Type_Ppp_2')) or (((/config_data/main/ComPort_3/RR_ComPort_3_ENA != 'On') or (/config_data/main/ComPort_3/RR_ComPort_3_Protocol != 'PPP')) and (../LinkMngLink_Type = 'LB_LinkMngLink_Type_Ppp_3')) or ((/config_data/main/Networking/RR_PppoeClient_Enable != 'On') and (../LinkMngLink_Type = 'LB_LinkMngLink_Type_Pppoe_Client')))))";
                    default "On";
                }
                leaf "LinkMngLink_Type" {
                    type "enumeration" {
                        enum "LB_LinkMngLink_Type_Static" {
                            value "0";
                        }
                        enum "LB_LinkMngLink_Type_WWAN_MAIN" {
                            value "1";
                        }
                        enum "LB_LinkMngLink_Type_WWAN_EXT" {
                            value "2";
                        }
                        enum "LB_LinkMngLink_Type_Ppp_1" {
                            value "3";
                        }
                        enum "LB_LinkMngLink_Type_Ppp_2" {
                            value "4";
                        }
                        enum "LB_LinkMngLink_Type_Ppp_3" {
                            value "5";
                        }
                        enum "LB_LinkMngLink_Type_Pppoe_Client" {
                            value "6";
                        }
                    }
                    must "not ((. = 'LB_LinkMngLink_Type_WWAN_MAIN' and (/config_data/device/DeviceHw/RR_DynHw_Primary_Cellular != 'On')) or (. = 'LB_LinkMngLink_Type_WWAN_EXT' and ((/config_data/device/DeviceHw/RR_DynHw_Module_Cellular != 'On') and (/config_data/device/DeviceHw/RR_DynHw_Module_Wifi != 'On'))) or (. = 'LB_LinkMngLink_Type_Ppp_1' and (/config_data/device/DeviceHw/RR_DynHw_Port_Com1 != 'On')) or (. = 'LB_LinkMngLink_Type_Ppp_2' and (/config_data/device/DeviceHw/RR_DynHw_Port_Com2 != 'On')) or (. = 'LB_LinkMngLink_Type_Ppp_3' and (/config_data/device/DeviceHw/RR_DynHw_Port_Com3 != 'On')))";
                    default "LB_LinkMngLink_Type_Static";
                }
                leaf "LinkMngLink_Tst_TestPeriod" {
                    when "not (../LinkMngLink_Testing != 'On')";
                    type "uint16" {
                        range "3..3600";
                    }
                    default "60";
                }
                leaf "LinkMngLink_Note" {
                    type "string" {
                        pattern "[^\"`\\\\$;]{0,42}";
                    }
                    default "";
                }
                leaf "LinkMngLink_Label" {
                    type "string" {
                        pattern "[a-zA-Z0-9@._-]{1,42}";
                    }
                    default "LINK";
                }
                leaf "LinkMngLink_NextHop" {
                    when "not (../LinkMngLink_Type != 'LB_LinkMngLink_Type_Static')";
                    type "inet:ipv4-address";
                    default "0.0.0.0";
                }
                leaf "LinkMngLink_Watch_ETH1" {
                    when "not ((../LinkMngLink_Type != 'LB_LinkMngLink_Type_Static') or (/config_data/device/DeviceHw/RR_DynHw_Port_Eth_Cnt <= 0) or (/config_data/main/EthPorts/RR_EthPort_1_Enable != 'On'))";
                    type "lbox_off_on";
                    default "Off";
                }
                leaf "LinkMngLink_Watch_ETH2" {
                    when "not ((../LinkMngLink_Type != 'LB_LinkMngLink_Type_Static') or (/config_data/device/DeviceHw/RR_DynHw_Port_Eth_Cnt <= 1) or (/config_data/main/EthPorts/RR_EthPort_2_Enable != 'On'))";
                    type "lbox_off_on";
                    default "Off";
                }
                leaf "LinkMngLink_Watch_ETH3" {
                    when "not ((../LinkMngLink_Type != 'LB_LinkMngLink_Type_Static') or (/config_data/device/DeviceHw/RR_DynHw_Port_Eth_Cnt <= 2) or (/config_data/main/EthPorts/RR_EthPort_3_Enable != 'On'))";
                    type "lbox_off_on";
                    default "Off";
                }
                leaf "LinkMngLink_Watch_ETH4" {
                    when "not ((../LinkMngLink_Type != 'LB_LinkMngLink_Type_Static') or (/config_data/device/DeviceHw/RR_DynHw_Port_Eth_Cnt <= 3) or (/config_data/main/EthPorts/RR_EthPort_4_Enable != 'On'))";
                    type "lbox_off_on";
                    default "Off";
                }
                leaf "LinkMngLink_Tst_RepeatPeriod" {
                    when "not (../LinkMngLink_Testing != 'On')";
                    type "uint16" {
                        range "3..3600";
                    }
                    default "10";
                }
                leaf "LinkMngLink_Watch_ETH5" {
                    when "not ((../LinkMngLink_Type != 'LB_LinkMngLink_Type_Static') or (/config_data/device/DeviceHw/RR_DynHw_Port_Sfp != 'On') or (/config_data/main/ExtensionPorts/RR_PortSfpEnable != 'On'))";
                    type "lbox_off_on";
                    default "Off";
                }
                leaf "LinkMngLink_Watch_Radio" {
                    when "not ((../LinkMngLink_Type != 'LB_LinkMngLink_Type_Static') or (/config_data/device/DeviceHw/RR_DynHw_Primary_Radio != 'On'))";
                    type "lbox_off_on";
                    default "Off";
                }
                leaf "LinkMngLink_Tst_WaitTime" {
                    when "not (../LinkMngLink_Testing != 'On')";
                    type "uint8" {
                        range "1..60";
                    }
                    default "5";
                }
                leaf "LinkMngLink_IpSecAssociation_ID" {
                    when "not ((/config_data/main/VPN/RR_IpSecEnable != 'On') or (/config_data/main/LinkManager/RR_LinkMng_IpSecControl != 'On'))";
                    type "lim_uint_16";
                    default "0";
                }
                leaf "LinkMngLink_Testing" {
                    type "lbox_off_on";
                    default "Off";
                }
                leaf "LinkMngLink_Tst_PassCnt" {
                    when "not (../LinkMngLink_Testing != 'On')";
                    type "uint8" {
                        range "1..20";
                    }
                    default "1";
                }
                leaf "LinkMngLink_Tst_FailCnt" {
                    when "not (../LinkMngLink_Testing != 'On')";
                    type "uint8" {
                        range "1..20";
                    }
                    default "3";
                }
                leaf "LinkMngLink_Tst_UseBackupAddr" {
                    when "not (../LinkMngLink_Testing != 'On')";
                    type "lbox_off_on";
                    default "Off";
                }
                leaf "LinkMngLink_Tst_EvaluationType" {
                    when "not ((../LinkMngLink_Testing != 'On') or (../LinkMngLink_Tst_UseBackupAddr != 'On'))";
                    type "lbox_test_2_evaluation";
                    default "LB_CellLT_ProfileSwitch_One_succeeds";
                }
                leaf "LinkMngLink_Tst_TestWhenBackup" {
                    when "not (../LinkMngLink_Testing != 'On')";
                    type "lbox_off_on";
                    default "On";
                }
                leaf "LinkMngLink_Tst_TestAddr" {
                    when "not (../LinkMngLink_Testing != 'On')";
                    type "string" {
                        pattern "[a-zA-Z0-9.-]{1,128}";
                    }
                    default "0.0.0.0";
                }
                leaf "LinkMngLink_Tst_BackupTestAddr" {
                    when "not ((../LinkMngLink_Testing != 'On') or (../LinkMngLink_Tst_UseBackupAddr != 'On'))";
                    type "string" {
                        pattern "[a-zA-Z0-9.-]{1,128}";
                    }
                    default "0.0.0.0";
                }
            }
            list "RR_S_TABLE_IpSecAssociations" {
                when "not (/config_data/main/VPN/RR_IpSecEnable != 'On')";
                key "ID";
                max-elements "24";
                leaf "ID" {
                    type "lim_uint_16";
                }
                leaf "IpSecA_ItActive" {
                    type "enumeration" {
                        enum "Off" {
                            value "0";
                        }
                        enum "On" {
                            value "1";
                        }
                    }
                    must "not ((. = 'On' and ((../IpSecA_Management != 'LB_IpSecA_Management_Off') and ((/config_data/main/Networking/RR_LinkManagerEn != 'On') or (/config_data/main/LinkManager/RR_LinkMng_IpSecControl != 'On')))))";
                    default "On";
                }
                leaf "IpSecA_IKEVersion" {
                    type "enumeration" {
                        enum "IKEv1" {
                            value "0";
                        }
                        enum "IKEv2" {
                            value "1";
                        }
                    }
                    default "IKEv2";
                }
                leaf "IpSecA_StartState" {
                    type "enumeration" {
                        enum "Passive" {
                            value "0";
                        }
                        enum "On Demand" {
                            value "1";
                        }
                        enum "Start" {
                            value "2";
                        }
                    }
                    default "Passive";
                }
                leaf "IpSecA_MOBIKE" {
                    when "not (../IpSecA_IKEVersion = 'IKEv1')";
                    type "lbox_off_on";
                    default "On";
                }
                leaf "IpSecA_DPDEnable" {
                    type "lbox_off_on";
                    default "Off";
                }
                leaf "IpSecA_DPDAction" {
                    when "not (../IpSecA_DPDEnable != 'On')";
                    type "enumeration" {
                        enum "Clear" {
                            value "0";
                        }
                        enum "Hold" {
                            value "1";
                        }
                        enum "Restart" {
                            value "2";
                        }
                    }
                    default "Hold";
                }
                leaf "IpSecA_Note" {
                    type "string" {
                        pattern "[^\"`\\\\$;]{0,42}";
                    }
                    default "";
                }
                leaf "IpSecA_LocalAddr" {
                    type "inet:ipv4-address";
                    default "0.0.0.0";
                }
                leaf "IpSecA_PeerAddr" {
                    type "inet:ipv4-address";
                    default "0.0.0.0";
                }
                leaf "IpSecA_DPDPeriod" {
                    when "not (../IpSecA_DPDEnable != 'On')";
                    type "uint16" {
                        range "5..28800";
                    }
                    default "30";
                }
                leaf "IpSecA_Authentication" {
                    type "enumeration" {
                        enum "PSK" {
                            value "0";
                        }
                    }
                    default "PSK";
                }
                leaf "IpSecA_IKE_AEAD_ICV" {
                    when "not ((../IpSecA_IKEVersion != 'IKEv2') or (../IpSecA_IKE_Encryption != 'AES128CCM (AEAD)' and ../IpSecA_IKE_Encryption != 'AES192CCM (AEAD)' and ../IpSecA_IKE_Encryption != 'AES256CCM (AEAD)' and ../IpSecA_IKE_Encryption != 'AES128GCM (AEAD)' and ../IpSecA_IKE_Encryption != 'AES192GCM (AEAD)' and ../IpSecA_IKE_Encryption != 'AES256GCM (AEAD)'))";
                    type "enumeration" {
                        enum "64b" {
                            value "0";
                        }
                        enum "96b" {
                            value "1";
                        }
                        enum "128b" {
                            value "2";
                        }
                    }
                    default "96b";
                }
                leaf "IpSecA_IKE_Integrity" {
                    when "not (../IpSecA_IKE_Encryption = 'AES128CCM (AEAD)' and ../IpSecA_IKE_Encryption = 'AES192CCM (AEAD)' and ../IpSecA_IKE_Encryption = 'AES256CCM (AEAD)' and ../IpSecA_IKE_Encryption = 'AES128GCM (AEAD)' and ../IpSecA_IKE_Encryption = 'AES192GCM (AEAD)' and ../IpSecA_IKE_Encryption = 'AES256GCM (AEAD)' and ../IpSecA_IKE_Encryption = 'ChaCha20Poly1305 (AEAD)')";
                    type "lbox_ipsec_integrity";
                    default "SHA256";
                }
                leaf "IpSecA_IKE_DHGroup" {
                    type "enumeration" {
                        enum "Group 2 (MODP1024, legacy)" {
                            value "1";
                        }
                        enum "Group 5 (MODP1536, legacy)" {
                            value "2";
                        }
                        enum "Group 14 (MODP2048)" {
                            value "3";
                        }
                        enum "Group 15 (MODP3072)" {
                            value "4";
                        }
                        enum "Group 25 (ECP192)" {
                            value "5";
                        }
                        enum "Group 26 (ECP224)" {
                            value "6";
                        }
                        enum "Group 19 (ECP256)" {
                            value "7";
                        }
                        enum "Group 20 (ECP384)" {
                            value "8";
                        }
                        enum "Group 21 (ECP521)" {
                            value "9";
                        }
                        enum "Group 27 (ECP224BP)" {
                            value "10";
                        }
                        enum "Group 28 (ECP256BP)" {
                            value "11";
                        }
                        enum "Group 29 (ECP384BP)" {
                            value "12";
                        }
                        enum "Group 30 (ECP512BP)" {
                            value "13";
                        }
                        enum "Group 31 (X25519)" {
                            value "14";
                        }
                        enum "Group 32 (X448)" {
                            value "15";
                        }
                    }
                    default "Group 15 (MODP3072)";
                }
                leaf "IpSecA_IKEv2_Reauth" {
                    when "not (../IpSecA_IKEVersion = 'IKEv1')";
                    type "lbox_off_on";
                    default "Off";
                }
                leaf "IpSecA_Management" {
                    type "enumeration" {
                        enum "LB_IpSecA_Management_Off" {
                            value "0";
                        }
                        enum "LB_IpSecA_Management_LM_Master" {
                            value "1";
                        }
                        enum "LB_IpSecA_Management_LM_Slave" {
                            value "2";
                        }
                    }
                    must "not ((. = 'LB_IpSecA_Management_LM_Master' and (../IpSecA_OperationMode != 'LB_IpSecA_OperationMode_Tunnel')) or (. = 'LB_IpSecA_Management_LM_Slave' and (../IpSecA_OperationMode != 'LB_IpSecA_OperationMode_Tunnel')))";
                    default "LB_IpSecA_Management_Off";
                }
                leaf "IpSecA_IKE_Encryption" {
                    type "enumeration" {
                        enum "3DES (legacy)" {
                            value "0";
                        }
                        enum "AES128" {
                            value "1";
                        }
                        enum "AES192" {
                            value "2";
                        }
                        enum "AES256" {
                            value "3";
                        }
                        enum "AES128CCM (AEAD)" {
                            value "4";
                        }
                        enum "AES192CCM (AEAD)" {
                            value "5";
                        }
                        enum "AES256CCM (AEAD)" {
                            value "6";
                        }
                        enum "AES128GCM (AEAD)" {
                            value "7";
                        }
                        enum "AES192GCM (AEAD)" {
                            value "8";
                        }
                        enum "AES256GCM (AEAD)" {
                            value "9";
                        }
                        enum "ChaCha20Poly1305 (AEAD)" {
                            value "10";
                        }
                    }
                    must "not ((. = 'AES128CCM (AEAD)' and (../IpSecA_IKEVersion != 'IKEv2')) or (. = 'AES192CCM (AEAD)' and (../IpSecA_IKEVersion != 'IKEv2')) or (. = 'AES256CCM (AEAD)' and (../IpSecA_IKEVersion != 'IKEv2')) or (. = 'AES128GCM (AEAD)' and (../IpSecA_IKEVersion != 'IKEv2')) or (. = 'AES192GCM (AEAD)' and (../IpSecA_IKEVersion != 'IKEv2')) or (. = 'AES256GCM (AEAD)' and (../IpSecA_IKEVersion != 'IKEv2')) or (. = 'ChaCha20Poly1305 (AEAD)' and (../IpSecA_IKEVersion != 'IKEv2')))";
                    default "AES128";
                }
                leaf "IpSecA_IKE_PseudoRndFun" {
                    when "not ((../IpSecA_IKEVersion != 'IKEv2') or (../IpSecA_IKE_Encryption != 'AES128CCM (AEAD)' and ../IpSecA_IKE_Encryption != 'AES192CCM (AEAD)' and ../IpSecA_IKE_Encryption != 'AES256CCM (AEAD)' and ../IpSecA_IKE_Encryption != 'AES128GCM (AEAD)' and ../IpSecA_IKE_Encryption != 'AES192GCM (AEAD)' and ../IpSecA_IKE_Encryption != 'AES256GCM (AEAD)' and ../IpSecA_IKE_Encryption != 'ChaCha20Poly1305 (AEAD)'))";
                    type "enumeration" {
                        enum "SHA256" {
                            value "0";
                        }
                        enum "SHA384" {
                            value "1";
                        }
                        enum "SHA512" {
                            value "2";
                        }
                    }
                    default "SHA256";
                }
                leaf "IpSecA_IKEv2_UsePostQPSK" {
                    when "not (../IpSecA_IKEVersion != 'IKEv2')";
                    type "lbox_off_on";
                    default "Off";
                }
                leaf "IpSecA_IpSec_Encryption" {
                    type "lbox_IpSecA_IKE_Encryption_M1";
                    must "not ((. = 'AES128CCM (AEAD)' and (../IpSecA_IKEVersion != 'IKEv2')) or (. = 'AES192CCM (AEAD)' and (../IpSecA_IKEVersion != 'IKEv2')) or (. = 'AES256CCM (AEAD)' and (../IpSecA_IKEVersion != 'IKEv2')) or (. = 'AES128GCM (AEAD)' and (../IpSecA_IKEVersion != 'IKEv2')) or (. = 'AES192GCM (AEAD)' and (../IpSecA_IKEVersion != 'IKEv2')) or (. = 'AES256GCM (AEAD)' and (../IpSecA_IKEVersion != 'IKEv2')) or (. = 'ChaCha20Poly1305 (AEAD)' and (../IpSecA_IKEVersion != 'IKEv2')))";
                    default "AES128";
                }
                leaf "IpSecA_OperationMode" {
                    type "enumeration" {
                        enum "LB_IpSecA_OperationMode_Tunnel" {
                            value "0";
                        }
                        enum "LB_IpSecA_OperationMode_Transport" {
                            value "1";
                        }
                    }
                    default "LB_IpSecA_OperationMode_Tunnel";
                }
                leaf "IpSecA_IKEv2_PostQPSK_Id" {
                    when "not ((../IpSecA_IKEVersion != 'IKEv2') or (../IpSecA_IKEv2_UsePostQPSK != 'On'))";
                    type "string" {
                        pattern "[a-zA-Z0-9@.-]{0,64}";
                    }
                    default "";
                }
                leaf "IpSecA_IKEv2_PostQPSK_KeyId" {
                    when "not ((../IpSecA_IKEVersion != 'IKEv2') or (../IpSecA_IKEv2_UsePostQPSK != 'On'))";
                    type "string" {
                        pattern "[a-zA-Z0-9_]{0,128}";
                    }
                    default "";
                }
                leaf "IpSecA_LocalId" {
                    type "string" {
                        pattern "[a-zA-Z0-9@.-]{1,64}";
                    }
                    mandatory "true";
                }
                leaf "IpSecA_PeerId" {
                    type "string" {
                        pattern "[a-zA-Z0-9@.-]{1,64}";
                    }
                    mandatory "true";
                }
                leaf "IpSecA_IKE_SALifetime" {
                    type "uint32" {
                        range "300..86400";
                    }
                    default "14400";
                }
                leaf "IpSecA_IpSec_AEAD_ICV" {
                    when "not ((../IpSecA_IKEVersion != 'IKEv2') or (../IpSecA_IpSec_Encryption != 'AES128CCM (AEAD)' and ../IpSecA_IpSec_Encryption != 'AES192CCM (AEAD)' and ../IpSecA_IpSec_Encryption != 'AES256CCM (AEAD)' and ../IpSecA_IpSec_Encryption != 'AES128GCM (AEAD)' and ../IpSecA_IpSec_Encryption != 'AES192GCM (AEAD)' and ../IpSecA_IpSec_Encryption != 'AES256GCM (AEAD)'))";
                    type "lbox_IpSecA_IKE_AEAD_ICV";
                    default "96b";
                }
                leaf "IpSecA_IpSec_Integrity" {
                    when "not (../IpSecA_IpSec_Encryption = 'AES128CCM (AEAD)' and ../IpSecA_IpSec_Encryption = 'AES192CCM (AEAD)' and ../IpSecA_IpSec_Encryption = 'AES256CCM (AEAD)' and ../IpSecA_IpSec_Encryption = 'AES128GCM (AEAD)' and ../IpSecA_IpSec_Encryption = 'AES192GCM (AEAD)' and ../IpSecA_IpSec_Encryption = 'AES256GCM (AEAD)' and ../IpSecA_IpSec_Encryption = 'ChaCha20Poly1305 (AEAD)')";
                    type "lbox_ipsec_integrity";
                    default "SHA256";
                }
                leaf "IpSecA_IpSec_DHGroup" {
                    type "enumeration" {
                        enum "None (legacy)" {
                            value "0";
                        }
                        enum "Group 2 (MODP1024, legacy)" {
                            value "1";
                        }
                        enum "Group 5 (MODP1536, legacy)" {
                            value "2";
                        }
                        enum "Group 14 (MODP2048)" {
                            value "3";
                        }
                        enum "Group 15 (MODP3072)" {
                            value "4";
                        }
                        enum "Group 25 (ECP192)" {
                            value "5";
                        }
                        enum "Group 26 (ECP224)" {
                            value "6";
                        }
                        enum "Group 19 (ECP256)" {
                            value "7";
                        }
                        enum "Group 20 (ECP384)" {
                            value "8";
                        }
                        enum "Group 21 (ECP521)" {
                            value "9";
                        }
                        enum "Group 27 (ECP224BP)" {
                            value "10";
                        }
                        enum "Group 28 (ECP256BP)" {
                            value "11";
                        }
                        enum "Group 29 (ECP384BP)" {
                            value "12";
                        }
                        enum "Group 30 (ECP512BP)" {
                            value "13";
                        }
                        enum "Group 31 (X25519)" {
                            value "14";
                        }
                        enum "Group 32 (X448)" {
                            value "15";
                        }
                    }
                    default "Group 15 (MODP3072)";
                }
                leaf "IpSecA_IpSec_Compression" {
                    type "lbox_off_on";
                    default "Off";
                }
                leaf "IpSecA_IpSec_TFCPadding" {
                    type "lbox_off_on";
                    default "Off";
                }
                leaf "IpSecA_PSK_Mode" {
                    type "lbox_psk_key_mode";
                    default "Pass Phrase";
                }
                leaf "IpSecA_IpSec_SALifetime" {
                    type "uint32" {
                        range "180..86400";
                    }
                    default "3600";
                }
                leaf "IpSecA_PSK_KeyId" {
                    when "not (../IpSecA_PSK_Mode != 'Key')";
                    type "string" {
                        pattern "[a-zA-Z0-9_]{0,128}";
                    }
                    default "";
                }
                leaf "IpSecA_PSK_Phrase" {
                    when "not (../IpSecA_PSK_Mode != 'Pass Phrase')";
                    type "string" {
                        pattern ".{0,128}";
                    }
                    default "";
                }
            }
            list "RR_S_TABLE_IpSecTrafficSelectors" {
                when "not (/config_data/main/VPN/RR_IpSecEnable != 'On')";
                key "ID";
                max-elements "48";
                ordered-by "user";
                leaf "ID" {
                    type "lim_uint_16";
                }
                leaf "ID_Parent" {
                    type "lim_uint_16";
                    default "0";
                }
                leaf "IpSecTS_ItActive" {
                    type "lbox_off_on";
                    default "On";
                }
                leaf "IpSecTS_LocalNetMask" {
                    type "lim_ipv4_mask0";
                    default "32";
                }
                leaf "IpSecTS_RemoteNetMask" {
                    type "lim_ipv4_mask0";
                    default "32";
                }
                leaf "IpSecTS_Note" {
                    type "string" {
                        pattern "[^\"`\\\\$;]{0,42}";
                    }
                    default "";
                }
                leaf "IpSecTS_LocalNetAddr" {
                    type "inet:ipv4-address";
                    default "0.0.0.0";
                }
                leaf "IpSecTS_RemoteNetAddr" {
                    type "inet:ipv4-address";
                    default "0.0.0.0";
                }
                leaf "IpSecTS_Protocol" {
                    type "lbox_l3_protocol";
                    default "All";
                }
                leaf "IpSecTS_LeakPrevention" {
                    type "lbox_ipsec_leak_prevention";
                    default "LB_ipsec_leak_prevention_V_Exact";
                }
                leaf "IpSecTS_ProtocolNum" {
                    when "not (../IpSecTS_Protocol != 'Other')";
                    type "lim_uint_8_1toFF";
                    default "1";
                }
            }
            list "RR_S_TABLE_IpSecTrafficSelectorsTransport" {
                when "not (/config_data/main/VPN/RR_IpSecEnable != 'On')";
                key "ID";
                max-elements "48";
                ordered-by "user";
                description "Cnf. group for IPsec: row of table IpSecTrafficSelectorTransport";
                leaf "ID" {
                    type "lim_uint_16";
                }
                leaf "ID_Parent" {
                    type "lim_uint_16";
                    default "0";
                }
                leaf "IpSecTS_ItActive" {
                    type "lbox_off_on";
                    default "On";
                }
                leaf "IpSecTS_Note" {
                    type "string" {
                        pattern "[^\"`\\\\$;]{0,42}";
                    }
                    default "";
                }
                leaf "IpSecTS_Protocol" {
                    type "lbox_l3_protocol";
                    default "All";
                }
                leaf "IpSecTS_LeakPrevention" {
                    type "lbox_ipsec_leak_prevention";
                    default "LB_ipsec_leak_prevention_V_Exact";
                }
                leaf "IpSecTS_ProtocolNumTransport" {
                    when "not (../IpSecTS_Protocol != 'Other')";
                    type "lim_uint_8_1toFF";
                    default "1";
                }
            }
            list "RR_S_TABLE_GreL2Tunnels" {
                when "not (/config_data/main/VPN/RR_GreL2Enable != 'On')";
                key "ID";
                max-elements "256";
                leaf "ID" {
                    type "lim_uint_16";
                }
                leaf "ID_Parent" {
                    type "lim_uint_16";
                    default "0";
                }
                leaf "GreL2Tun_ItActive" {
                    type "lbox_off_on";
                    default "On";
                }
                leaf "GreL2Tun_KeyEn" {
                    type "lbox_off_on";
                    default "Off";
                }
                leaf "GreL2Tun_Mtu" {
                    type "uint16" {
                        range "74..1500";
                    }
                    default "1462";
                }
                leaf "GreL2Tun_Note" {
                    type "string" {
                        pattern "[^\"`\\\\$;]{0,42}";
                    }
                    default "";
                }
                leaf "GreL2Tun_PeerAddr" {
                    type "inet:ipv4-address";
                    default "0.0.0.0";
                }
                leaf "GreL2Tun_Key" {
                    when "not (../GreL2Tun_KeyEn != 'On')";
                    type "lim_uint_32";
                    default "0";
                }
                leaf "GreL2Tun_TunName" {
                    type "string" {
                        pattern "[a-zA-Z0-9_-]{1,11}";
                    }
                    default "tap0";
                }
            }
            list "RR_S_TABLE_GreL3Tunnels" {
                when "not (/config_data/main/VPN/RR_GreL3Enable != 'On')";
                key "ID";
                max-elements "256";
                leaf "ID" {
                    type "lim_uint_16";
                }
                leaf "GreL3Tun_ItActive" {
                    type "lbox_off_on";
                    default "On";
                }
                leaf "GreL3Tun_KeyEn" {
                    type "lbox_off_on";
                    default "Off";
                }
                leaf "GreL3Tun_TunnelMask" {
                    type "lim_ipv4_mask";
                    default "32";
                }
                leaf "GreL3Tun_Note" {
                    type "string" {
                        pattern "[^\"`\\\\$;]{0,42}";
                    }
                    default "";
                }
                leaf "GreL3Tun_PeerAddr" {
                    type "inet:ipv4-address";
                    default "0.0.0.0";
                }
                leaf "GreL3Tun_TunnelAddr" {
                    type "inet:ipv4-address";
                    default "0.0.0.0";
                }
                leaf "GreL3Tun_Mtu" {
                    type "uint16" {
                        range "70..1476";
                    }
                    default "1476";
                }
                leaf "GreL3Tun_MngEn" {
                    type "lbox_off_on";
                    default "On";
                }
                leaf "GreL3Tun_RmtAccEn" {
                    when "not (/config_data/main/UserAccess/RR_UsAcc_RmtAccess_Enable != 'On')";
                    type "lbox_off_on";
                    default "Off";
                }
                leaf "GreL3Tun_Key" {
                    when "not (../GreL3Tun_KeyEn != 'On')";
                    type "lim_uint_32";
                    default "0";
                }
                leaf "GreL3Tun_TunName" {
                    type "string" {
                        pattern "[a-zA-Z0-9_-]{1,11}";
                    }
                    default "tun0";
                }
            }
            list "RR_S_TABLE_OvpnTunnels" {
                when "not (/config_data/main/VPN/RR_OpenVpnEnable != 'On')";
                key "ID";
                max-elements "4";
                ordered-by "user";
                leaf "ID" {
                    type "lim_uint_16";
                }
                leaf "OvpnTun_ItActive" {
                    type "lbox_off_on";
                    default "On";
                }
                leaf "OvpnTun_Mode" {
                    type "enumeration" {
                        enum "LB_OvpnTun_Mode_Client" {
                            value "0";
                        }
                        enum "LB_OvpnTun_Mode_Server" {
                            value "1";
                        }
                    }
                    default "LB_OvpnTun_Mode_Client";
                }
                leaf "OvpnTun_Iface_Mode" {
                    type "enumeration" {
                        enum "LB_OvpnTun_Iface_Mode_Bridge" {
                            value "0";
                        }
                        enum "LB_OvpnTun_Iface_Mode_Router" {
                            value "1";
                        }
                    }
                    default "LB_OvpnTun_Iface_Mode_Router";
                }
                leaf "OvpnTun_Net_DynamicClAddrs" {
                    when "not ((../OvpnTun_Mode != 'LB_OvpnTun_Mode_Server') or (../OvpnTun_Iface_Mode != 'LB_OvpnTun_Iface_Mode_Router'))";
                    type "lbox_off_on";
                    default "Off";
                }
                leaf "OvpnTun_Net_Topology" {
                    when "not ((../OvpnTun_Mode != 'LB_OvpnTun_Mode_Server') or (../OvpnTun_Iface_Mode != 'LB_OvpnTun_Iface_Mode_Router'))";
                    type "enumeration" {
                        enum "LB_OvpnTun_Net_Topology_Subnet" {
                            value "0";
                        }
                        enum "LB_OvpnTun_Net_Topology_Net30" {
                            value "1";
                        }
                    }
                    default "LB_OvpnTun_Net_Topology_Subnet";
                }
                leaf "OvpnTun_Iface_Mtu" {
                    type "uint16" {
                        range "100..1500";
                    }
                    default "1500";
                }
                leaf "OvpnTun_Note" {
                    type "string" {
                        pattern "[^\"`\\\\$;]{0,42}";
                    }
                    default "";
                }
                leaf "OvpnTun_Iface_Name" {
                    type "string" {
                        pattern "[a-zA-Z0-9_-]{1,10}";
                    }
                    default "tun0";
                }
                leaf "OvpnTun_Iface_BridgeId" {
                    when "not (../OvpnTun_Iface_Mode != 'LB_OvpnTun_Iface_Mode_Bridge')";
                    type "lim_uint_16";
                    default "0";
                }
                leaf "OvpnTun_Net_IfAddr" {
                    when "not ((../OvpnTun_Mode != 'LB_OvpnTun_Mode_Server') or (../OvpnTun_Iface_Mode != 'LB_OvpnTun_Iface_Mode_Router'))";
                    type "inet:ipv4-address";
                    default "10.8.0.0";
                }
                leaf "OvpnTun_Net_IfMask" {
                    when "not ((../OvpnTun_Mode != 'LB_OvpnTun_Mode_Server') or (../OvpnTun_Iface_Mode != 'LB_OvpnTun_Iface_Mode_Router'))";
                    type "uint8" {
                        range "16..29";
                    }
                    default "24";
                }
                leaf "OvpnTun_Auth_CheckEKU" {
                    type "lbox_off_on";
                    default "On";
                }
                leaf "OvpnTun_Iface_MngEn" {
                    when "not (../OvpnTun_Iface_Mode != 'LB_OvpnTun_Iface_Mode_Router')";
                    type "lbox_off_on";
                    default "On";
                }
                leaf "OvpnTun_Iface_Masquerade" {
                    when "not ((../OvpnTun_Mode != 'LB_OvpnTun_Mode_Client') or (../OvpnTun_Iface_Mode != 'LB_OvpnTun_Iface_Mode_Router'))";
                    type "lbox_off_on";
                    default "Off";
                }
                leaf "OvpnTun_Crypt_CipherAlg" {
                    type "enumeration" {
                        enum "Default" {
                            value "0";
                        }
                        enum "AES-128-CBC" {
                            value "1";
                        }
                        enum "AES-128-CFB" {
                            value "2";
                        }
                        enum "AES-128-CFB1" {
                            value "3";
                        }
                        enum "AES-128-CFB8" {
                            value "4";
                        }
                        enum "AES-128-GCM" {
                            value "5";
                        }
                        enum "AES-128-OFB" {
                            value "6";
                        }
                        enum "AES-192-CBC" {
                            value "7";
                        }
                        enum "AES-192-CFB" {
                            value "8";
                        }
                        enum "AES-192-CFB1" {
                            value "9";
                        }
                        enum "AES-192-CFB8" {
                            value "10";
                        }
                        enum "AES-192-GCM" {
                            value "11";
                        }
                        enum "AES-192-OFB" {
                            value "12";
                        }
                        enum "AES-256-CBC" {
                            value "13";
                        }
                        enum "AES-256-CFB" {
                            value "14";
                        }
                        enum "AES-256-CFB1" {
                            value "15";
                        }
                        enum "AES-256-CFB8" {
                            value "16";
                        }
                        enum "AES-256-GCM" {
                            value "17";
                        }
                        enum "AES-256-OFB" {
                            value "18";
                        }
                        enum "ARIA-128-CBC" {
                            value "19";
                        }
                        enum "ARIA-128-CFB" {
                            value "20";
                        }
                        enum "ARIA-128-CFB1" {
                            value "21";
                        }
                        enum "ARIA-128-CFB8" {
                            value "22";
                        }
                        enum "ARIA-128-GCM" {
                            value "23";
                        }
                        enum "ARIA-128-OFB" {
                            value "24";
                        }
                        enum "ARIA-192-CBC" {
                            value "25";
                        }
                        enum "ARIA-192-CFB" {
                            value "26";
                        }
                        enum "ARIA-192-CFB1" {
                            value "27";
                        }
                        enum "ARIA-192-CFB8" {
                            value "28";
                        }
                        enum "ARIA-192-GCM" {
                            value "29";
                        }
                        enum "ARIA-192-OFB" {
                            value "30";
                        }
                        enum "ARIA-256-CBC" {
                            value "31";
                        }
                        enum "ARIA-256-CFB" {
                            value "32";
                        }
                        enum "ARIA-256-CFB1" {
                            value "33";
                        }
                        enum "ARIA-256-CFB8" {
                            value "34";
                        }
                        enum "ARIA-256-GCM" {
                            value "35";
                        }
                        enum "ARIA-256-OFB" {
                            value "36";
                        }
                        enum "CAMELLIA-128-CBC" {
                            value "37";
                        }
                        enum "CAMELLIA-128-CFB" {
                            value "38";
                        }
                        enum "CAMELLIA-128-CFB1" {
                            value "39";
                        }
                        enum "CAMELLIA-128-CFB8" {
                            value "40";
                        }
                        enum "CAMELLIA-128-OFB" {
                            value "41";
                        }
                        enum "CAMELLIA-192-CBC" {
                            value "42";
                        }
                        enum "CAMELLIA-192-CFB" {
                            value "43";
                        }
                        enum "CAMELLIA-192-CFB1" {
                            value "44";
                        }
                        enum "CAMELLIA-192-CFB8" {
                            value "45";
                        }
                        enum "CAMELLIA-192-OFB" {
                            value "46";
                        }
                        enum "CAMELLIA-256-CBC" {
                            value "47";
                        }
                        enum "CAMELLIA-256-CFB" {
                            value "48";
                        }
                        enum "CAMELLIA-256-CFB1" {
                            value "49";
                        }
                        enum "CAMELLIA-256-CFB8" {
                            value "50";
                        }
                        enum "CAMELLIA-256-OFB" {
                            value "51";
                        }
                        enum "CHACHA20-POLY1305" {
                            value "52";
                        }
                        enum "SM4-CBC" {
                            value "53";
                        }
                        enum "SM4-CFB" {
                            value "54";
                        }
                        enum "SM4-OFB" {
                            value "55";
                        }
                        enum "DES-EDE-CBC (legacy)" {
                            value "56";
                        }
                        enum "DES-EDE-CFB (legacy)" {
                            value "57";
                        }
                        enum "DES-EDE-OFB (legacy)" {
                            value "58";
                        }
                        enum "DES-EDE3-CBC (legacy)" {
                            value "59";
                        }
                        enum "DES-EDE3-CFB (legacy)" {
                            value "60";
                        }
                        enum "DES-EDE3-CFB1 (legacy)" {
                            value "61";
                        }
                        enum "DES-EDE3-CFB8 (legacy)" {
                            value "62";
                        }
                        enum "DES-EDE3-OFB (legacy)" {
                            value "63";
                        }
                    }
                    default "Default";
                }
                leaf "OvpnTun_Net_ClAddrsStart" {
                    when "not ((../OvpnTun_Mode != 'LB_OvpnTun_Mode_Server') or (../OvpnTun_Iface_Mode != 'LB_OvpnTun_Iface_Mode_Router') or (../OvpnTun_Net_DynamicClAddrs != 'On'))";
                    type "inet:ipv4-address";
                    must "(round(16777216 * number(substring-before(., \".\")) + 65536 * number(substring-before(substring-after(., \".\"), \".\")) + 256 * number(substring-before(substring-after(substring-after(., \".\"), \".\"), \".\")) + number(substring-after(substring-after(substring-after(., \".\"), \".\"), \".\")))) <= (round(16777216 * number(substring-before(../OvpnTun_Net_ClAddrsEnd, \".\")) + 65536 * number(substring-before(substring-after(../OvpnTun_Net_ClAddrsEnd, \".\"), \".\")) + 256 * number(substring-before(substring-after(substring-after(../OvpnTun_Net_ClAddrsEnd, \".\"), \".\"), \".\")) + number(substring-after(substring-after(substring-after(../OvpnTun_Net_ClAddrsEnd, \".\"), \".\"), \".\"))))" {
                        error-message "valmsg_it_OvpnTun_Net_ClAddrsStart";
                    }
                    default "10.8.0.100";
                }
                leaf "OvpnTun_Net_ClAddrsEnd" {
                    when "not ((../OvpnTun_Mode != 'LB_OvpnTun_Mode_Server') or (../OvpnTun_Iface_Mode != 'LB_OvpnTun_Iface_Mode_Router') or (../OvpnTun_Net_DynamicClAddrs != 'On'))";
                    type "inet:ipv4-address";
                    must "(round(16777216 * number(substring-before(., \".\")) + 65536 * number(substring-before(substring-after(., \".\"), \".\")) + 256 * number(substring-before(substring-after(substring-after(., \".\"), \".\"), \".\")) + number(substring-after(substring-after(substring-after(., \".\"), \".\"), \".\")))) >= (round(16777216 * number(substring-before(../OvpnTun_Net_ClAddrsStart, \".\")) + 65536 * number(substring-before(substring-after(../OvpnTun_Net_ClAddrsStart, \".\"), \".\")) + 256 * number(substring-before(substring-after(substring-after(../OvpnTun_Net_ClAddrsStart, \".\"), \".\"), \".\")) + number(substring-after(substring-after(substring-after(../OvpnTun_Net_ClAddrsStart, \".\"), \".\"), \".\"))))" {
                        error-message "valmsg_it_OvpnTun_Net_ClAddrsEnd";
                    }
                    default "10.8.0.200";
                }
                leaf "OvpnTun_Auth_PrivKeyId" {
                    type "string" {
                        pattern "[a-zA-Z0-9_]{0,128}";
                    }
                    default "";
                }
                leaf "OvpnTun_Auth_CertId" {
                    type "string" {
                        pattern "[a-zA-Z0-9_]{0,128}";
                    }
                    default "";
                }
                leaf "OvpnTun_Auth_CACertId" {
                    type "string" {
                        pattern "[a-zA-Z0-9_]{0,128}";
                    }
                    default "";
                }
                leaf "OvpnTun_Crypt_RenegPeriod" {
                    type "uint32" {
                        range "60..86400";
                    }
                    default "3600";
                }
                leaf "OvpnTun_Crypt_DigestAlg" {
                    type "enumeration" {
                        enum "MD5" {
                            value "0";
                        }
                        enum "MD5-SHA1" {
                            value "1";
                        }
                        enum "RIPEMD160" {
                            value "4";
                        }
                        enum "SM3" {
                            value "5";
                        }
                        enum "SHA1" {
                            value "6";
                        }
                        enum "SHA224" {
                            value "7";
                        }
                        enum "SHA256" {
                            value "8";
                        }
                        enum "SHA384" {
                            value "9";
                        }
                        enum "SHA512-224" {
                            value "10";
                        }
                        enum "SHA512-256" {
                            value "11";
                        }
                        enum "SHA512" {
                            value "12";
                        }
                        enum "SHA3-224" {
                            value "13";
                        }
                        enum "SHA3-256" {
                            value "14";
                        }
                        enum "SHA3-384" {
                            value "15";
                        }
                        enum "SHA3-512" {
                            value "16";
                        }
                        enum "BLAKE2s256" {
                            value "17";
                        }
                        enum "BLAKE2b512" {
                            value "18";
                        }
                    }
                    default "SHA1";
                }
                leaf "OvpnTun_Compr_Mode" {
                    type "enumeration" {
                        enum "LB_OvpnTun_Compr_Off" {
                            value "0";
                        }
                        enum "LB_OvpnTun_Compr_On" {
                            value "1";
                        }
                        enum "LB_OvpnTun_Compr_Asymmetric" {
                            value "2";
                        }
                    }
                    default "LB_OvpnTun_Compr_Off";
                }
                leaf "OvpnTun_Compr_Algorithm" {
                    when "not (../OvpnTun_Compr_Mode = 'LB_OvpnTun_Compr_Off')";
                    type "enumeration" {
                        enum "LZO" {
                            value "0";
                        }
                        enum "LZ4" {
                            value "1";
                        }
                        enum "LZ4v2" {
                            value "2";
                        }
                        enum "LB_OvpnTun_Compr_Algorithm_Migrate" {
                            value "3";
                        }
                    }
                    default "LZO";
                }
                leaf "OvpnTun_Session_Limit" {
                    when "not (../OvpnTun_Mode != 'LB_OvpnTun_Mode_Client')";
                    type "lbox_off_on";
                    default "Off";
                }
                leaf "OvpnTun_LinkFrag_Enable" {
                    when "not ((../OvpnTun_Mode != 'LB_OvpnTun_Mode_Server') or (../OvpnTun_Srv_Protocol != 'UDP'))";
                    type "lbox_off_on";
                    default "Off";
                }
                leaf "OvpnTun_LinkFrag_MaxSize" {
                    when "not ((../OvpnTun_Mode != 'LB_OvpnTun_Mode_Server') or (../OvpnTun_Srv_Protocol != 'UDP') or (../OvpnTun_LinkFrag_Enable != 'On'))";
                    type "lim_openvpn_link_frag_size";
                    default "1300";
                }
                leaf "OvpnTun_Route_Metric" {
                    when "not (../OvpnTun_Iface_Mode != 'LB_OvpnTun_Iface_Mode_Router')";
                    type "lim_routing_metric";
                    default "24";
                }
                leaf "OvpnTun_Route_LocalUseSrcAddr" {
                    when "not (../OvpnTun_Iface_Mode != 'LB_OvpnTun_Iface_Mode_Router')";
                    type "inet:ipv4-address";
                    default "0.0.0.0";
                }
                leaf "OvpnTun_Session_Length" {
                    when "not ((../OvpnTun_Mode != 'LB_OvpnTun_Mode_Client') or (../OvpnTun_Session_Limit != 'On'))";
                    type "uint32" {
                        range "300..86400";
                    }
                    default "3600";
                }
                leaf "OvpnTun_Srv_Protocol" {
                    when "not (../OvpnTun_Mode != 'LB_OvpnTun_Mode_Server')";
                    type "lbox_openvpn_protocol";
                    default "UDP";
                }
                leaf "OvpnTun_Keepalive_Enable" {
                    when "not (../OvpnTun_Mode != 'LB_OvpnTun_Mode_Server')";
                    type "lbox_off_on";
                    default "On";
                }
                leaf "OvpnTun_FixTcpMss" {
                    when "not (../OvpnTun_Mode != 'LB_OvpnTun_Mode_Server')";
                    type "lbox_off_on";
                    default "On";
                }
                leaf "OvpnTun_TlsProtection_Mode" {
                    when "not (../OvpnTun_Mode != 'LB_OvpnTun_Mode_Server')";
                    type "lbox_openvpn_tls_protection_mode";
                    default "LB_openvpn_tls_protection_mode_Off";
                }
                leaf "OvpnTun_TlsProtection_SharedKeyDir" {
                    when "not ((../OvpnTun_Mode != 'LB_OvpnTun_Mode_Server') or (../OvpnTun_TlsProtection_Mode != 'LB_openvpn_tls_protection_mode_TLS_Auth'))";
                    type "lbox_openvpn_tlsauth_key_dir";
                    default "0";
                }
                leaf "OvpnTun_ClMng_Client2Client" {
                    when "not (../OvpnTun_Mode != 'LB_OvpnTun_Mode_Server')";
                    type "lbox_off_on";
                    default "On";
                }
                leaf "OvpnTun_ClMng_AllowDupCN" {
                    when "not (../OvpnTun_Mode != 'LB_OvpnTun_Mode_Server')";
                    type "lbox_off_on";
                    default "Off";
                }
                leaf "OvpnTun_ClMng_KnownCNOnly" {
                    when "not (../OvpnTun_Mode != 'LB_OvpnTun_Mode_Server')";
                    type "lbox_off_on";
                    default "On";
                }
                leaf "OvpnTun_ClMng_MaxConnected" {
                    when "not (../OvpnTun_Mode != 'LB_OvpnTun_Mode_Server')";
                    type "uint8" {
                        range "1..30";
                    }
                    default "30";
                }
                leaf "OvpnTun_ClAuth_UsePass" {
                    when "not (../OvpnTun_Mode != 'LB_OvpnTun_Mode_Client')";
                    type "lbox_off_on";
                    default "Off";
                }
                leaf "OvpnTun_Auth_AllowLegacy" {
                    type "lbox_off_on";
                    default "Off";
                }
                leaf "OvpnTun_Srv_Port" {
                    when "not (../OvpnTun_Mode != 'LB_OvpnTun_Mode_Server')";
                    type "lim_udp_port";
                    default "1194";
                }
                leaf "OvpnTun_Srv_DHParamsId" {
                    when "not (../OvpnTun_Mode != 'LB_OvpnTun_Mode_Server')";
                    type "string" {
                        pattern "[a-zA-Z0-9_]{0,128}";
                    }
                    default "";
                }
                leaf "OvpnTun_Keepalive_Period" {
                    when "not ((../OvpnTun_Mode != 'LB_OvpnTun_Mode_Server') or (../OvpnTun_Keepalive_Enable != 'On'))";
                    type "uint16" {
                        range "10..3600";
                    }
                    must ". <= ../OvpnTun_Keepalive_Timeout - 1" {
                        error-message "valmsg_it_OvpnTun_Keepalive_Period";
                    }
                    default "10";
                }
                leaf "OvpnTun_Keepalive_Timeout" {
                    when "not ((../OvpnTun_Mode != 'LB_OvpnTun_Mode_Server') or (../OvpnTun_Keepalive_Enable != 'On'))";
                    type "uint16" {
                        range "30..14400";
                    }
                    must ". >= ../OvpnTun_Keepalive_Period + 1" {
                        error-message "valmsg_it_OvpnTun_Keepalive_Timeout";
                    }
                    default "60";
                }
                leaf "OvpnTun_TlsProtection_SharedKeyId" {
                    when "not ((../OvpnTun_Mode != 'LB_OvpnTun_Mode_Server') or (../OvpnTun_TlsProtection_Mode != 'LB_openvpn_tls_protection_mode_TLS_Auth' and ../OvpnTun_TlsProtection_Mode != 'LB_openvpn_tls_protection_mode_TLS_Crypt'))";
                    type "string" {
                        pattern "[a-zA-Z0-9_]{0,128}";
                    }
                    default "";
                }
                leaf "OvpnTun_ClAuth_Username" {
                    when "not ((../OvpnTun_Mode != 'LB_OvpnTun_Mode_Client') or (../OvpnTun_ClAuth_UsePass != 'On'))";
                    type "string" {
                        pattern ".{0,64}";
                    }
                    default "";
                }
                leaf "OvpnTun_ClAuth_Password" {
                    when "not ((../OvpnTun_Mode != 'LB_OvpnTun_Mode_Client') or (../OvpnTun_ClAuth_UsePass != 'On'))";
                    type "string" {
                        pattern ".{0,64}";
                    }
                    default "";
                }
                leaf "OvpnTun_Iface_RmtAccEn" {
                    when "not ((/config_data/main/UserAccess/RR_UsAcc_RmtAccess_Enable != 'On') or (../OvpnTun_Iface_Mode != 'LB_OvpnTun_Iface_Mode_Router'))";
                    type "lbox_off_on";
                    default "Off";
                }
            }
            list "RR_S_TABLE_OvpnRmtProfiles" {
                when "not (/config_data/main/VPN/RR_OpenVpnEnable != 'On')";
                key "ID";
                max-elements "64";
                ordered-by "user";
                leaf "ID" {
                    type "lim_uint_16";
                }
                leaf "ID_Parent" {
                    type "lim_uint_16";
                    default "0";
                }
                leaf "OvpnRmt_ItActive" {
                    type "lbox_off_on";
                    default "On";
                }
                leaf "OvpnRmt_Protocol" {
                    type "lbox_openvpn_protocol";
                    default "UDP";
                }
                leaf "OvpnRmt_AddrFloating" {
                    type "lbox_off_on";
                    default "Off";
                }
                leaf "OvpnRmt_Conn_PeriodMax" {
                    type "uint16" {
                        range "1..600";
                    }
                    must ". >= ../OvpnRmt_Conn_PeriodInit" {
                        error-message "valmsg_it_OvpnRmt_Conn_PeriodMax";
                    }
                    default "300";
                }
                leaf "OvpnRmt_Note" {
                    type "string" {
                        pattern "[^\"`\\\\$;]{0,42}";
                    }
                    default "";
                }
                leaf "OvpnRmt_Addr" {
                    type "string" {
                        pattern "[a-zA-Z0-9.-]{1,128}";
                    }
                    default "0.0.0.0";
                }
                leaf "OvpnRmt_Port" {
                    type "lim_udp_port";
                    default "1194";
                }
                leaf "OvpnRmt_Conn_PeriodInit" {
                    type "uint8" {
                        range "1..60";
                    }
                    must ". <= ../OvpnRmt_Conn_PeriodMax" {
                        error-message "valmsg_it_OvpnRmt_Conn_PeriodInit";
                    }
                    default "1";
                }
                leaf "OvpnRmt_Conn_Timeout" {
                    type "uint16" {
                        range "1..3600";
                    }
                    default "120";
                }
                leaf "OvpnRmt_LinkFrag_Enable" {
                    when "not (../OvpnRmt_Protocol != 'UDP')";
                    type "lbox_off_on";
                    default "Off";
                }
                leaf "OvpnRmt_FixTcpMss" {
                    type "lbox_off_on";
                    default "On";
                }
                leaf "OvpnRmt_TlsProtection_Mode" {
                    type "lbox_openvpn_tls_protection_mode";
                    default "LB_openvpn_tls_protection_mode_Off";
                }
                leaf "OvpnRmt_TlsProtection_SharedKeyDir" {
                    when "not (../OvpnRmt_TlsProtection_Mode != 'LB_openvpn_tls_protection_mode_TLS_Auth')";
                    type "lbox_openvpn_tlsauth_key_dir";
                    default "1";
                }
                leaf "OvpnRmt_LinkFrag_MaxSize" {
                    when "not ((../OvpnRmt_Protocol != 'UDP') or (../OvpnRmt_LinkFrag_Enable != 'On'))";
                    type "lim_openvpn_link_frag_size";
                    default "1300";
                }
                leaf "OvpnRmt_TlsProtection_SharedKeyId" {
                    when "not (../OvpnRmt_TlsProtection_Mode != 'LB_openvpn_tls_protection_mode_TLS_Auth' and ../OvpnRmt_TlsProtection_Mode != 'LB_openvpn_tls_protection_mode_TLS_Crypt')";
                    type "string" {
                        pattern "[a-zA-Z0-9_]{0,128}";
                    }
                    default "";
                }
            }
            list "RR_S_TABLE_OvpnClients" {
                when "not (/config_data/main/VPN/RR_OpenVpnEnable != 'On')";
                key "ID";
                max-elements "128";
                description "Cnf. group for OpenVPN: row of table OvpnClients";
                leaf "ID" {
                    type "lim_uint_16";
                }
                leaf "ID_Parent" {
                    type "lim_uint_16";
                    default "0";
                }
                leaf "OvpnCl_ItActive" {
                    type "lbox_off_on";
                    default "On";
                }
                leaf "OvpnCl_AddressMode" {
                    type "enumeration" {
                        enum "LB_OvpnCl_AddressMode_Dynamic" {
                            value "0";
                        }
                        enum "LB_OvpnCl_AddressMode_Static" {
                            value "1";
                        }
                    }
                    default "LB_OvpnCl_AddressMode_Dynamic";
                }
                leaf "OvpnCl_Note" {
                    type "string" {
                        pattern "[^\"`\\\\$;]{0,42}";
                    }
                    default "";
                }
                leaf "OvpnCl_CommonName" {
                    type "string" {
                        pattern "[a-zA-Z0-9_.@-]{0,256}";
                    }
                    default "";
                }
                leaf "OvpnCl_StaticAddress" {
                    when "not (../OvpnCl_AddressMode != 'LB_OvpnCl_AddressMode_Static')";
                    type "inet:ipv4-address";
                    default "0.0.0.0";
                }
            }
            list "RR_S_TABLE_OvpnServerRoutes" {
                when "not (/config_data/main/VPN/RR_OpenVpnEnable != 'On')";
                key "ID";
                max-elements "128";
                description "Cnf. group for OpenVPN: row of table OvpnServerRoutes";
                leaf "ID" {
                    type "lim_uint_16";
                }
                leaf "ID_Parent" {
                    type "lim_uint_16";
                    default "0";
                }
                leaf "OvpnSRt_ItActive" {
                    type "lbox_off_on";
                    default "On";
                }
                leaf "OvpnSRt_DstMask" {
                    type "lim_ipv4_mask0";
                    default "0";
                }
                leaf "OvpnSRt_Note" {
                    type "string" {
                        pattern "[^\"`\\\\$;]{0,42}";
                    }
                    default "";
                }
                leaf "OvpnSRt_DstAddr" {
                    type "inet:ipv4-address";
                    default "0.0.0.0";
                }
            }
            list "RR_S_TABLE_OvpnClientRoutes" {
                when "not (/config_data/main/VPN/RR_OpenVpnEnable != 'On')";
                key "ID";
                max-elements "512";
                description "Cnf. group for OpenVPN: row of table OvpnClientRoutes";
                leaf "ID" {
                    type "lim_uint_16";
                }
                leaf "ID_Parent" {
                    type "lim_uint_16";
                    default "0";
                }
                leaf "OvpnCRt_ItActive" {
                    type "lbox_off_on";
                    default "On";
                }
                leaf "OvpnCRt_DstMask" {
                    type "lim_ipv4_mask0";
                    default "0";
                }
                leaf "OvpnCRt_Note" {
                    type "string" {
                        pattern "[^\"`\\\\$;]{0,42}";
                    }
                    default "";
                }
                leaf "OvpnCRt_DstAddr" {
                    type "inet:ipv4-address";
                    default "0.0.0.0";
                }
            }
            list "RR_S_TABLE_SnmpNotifDsts" {
                when "not ((/config_data/main/SNMP/RR_SnmpMode = 'Off') or (/config_data/main/SNMP/RR_SnmpNotification = 'Off'))";
                key "ID";
                max-elements "16";
                leaf "ID" {
                    type "lim_uint_16";
                }
                leaf "SnmpNotifIpAddr" {
                    type "inet:ipv4-address";
                    default "0.0.0.0";
                }
                leaf "SnmpNotifIpPort" {
                    type "lim_udp_port";
                    default "162";
                }
            }
            list "RR_S_TABLE_NtpServers" {
                key "ID";
                max-elements "32";
                leaf "ID" {
                    type "lim_uint_16";
                }
                leaf "NtpServ_ItActive" {
                    type "lbox_off_on";
                    default "On";
                }
                leaf "NtpServ_Note" {
                    type "string" {
                        pattern "[^\"`\\\\$;]{0,42}";
                    }
                    default "";
                }
                leaf "NtpServ_Addr" {
                    type "string" {
                        pattern "[a-zA-Z0-9.-]{1,128}";
                    }
                    default "0.0.0.0";
                }
            }
            list "RR_S_TABLE_FwDistSndTargets" {
                when "not ((/config_data/device/DeviceHw/RR_DynHw_FwDistribution != 'On') or (/config_data/main/FwDistribution/RR_FwDist_SenderEn != 'On'))";
                key "ID";
                max-elements "300";
                description "Cnf. group for FW distribution: row of table FwDistSndTargets";
                leaf "ID" {
                    type "lim_uint_16";
                }
                leaf "FwDistSTrg_ItActive" {
                    type "lbox_off_on";
                    default "On";
                }
                leaf "FwDistSTrg_GroupA" {
                    type "lbox_off_on";
                    default "On";
                }
                leaf "FwDistSTrg_GroupB" {
                    type "lbox_off_on";
                    default "Off";
                }
                leaf "FwDistSTrg_GroupC" {
                    type "lbox_off_on";
                    default "Off";
                }
                leaf "FwDistSTrg_GroupD" {
                    type "lbox_off_on";
                    default "Off";
                }
                leaf "FwDistSTrg_Note" {
                    type "string" {
                        pattern "[^\"`\\\\$;]{0,42}";
                    }
                    default "";
                }
                leaf "FwDistSTrg_RadioAddr" {
                    type "inet:ipv4-address";
                    default "0.0.0.0";
                }
            }
            list "RR_S_TABLE_FwDistRcvSources" {
                when "not ((/config_data/device/DeviceHw/RR_DynHw_FwDistribution != 'On') or (/config_data/main/FwDistribution/RR_FwDist_ReceiverEn != 'On'))";
                key "ID";
                max-elements "16";
                description "Cnf. group for FW distribution: row of table FwDistRcvSources";
                leaf "ID" {
                    type "lim_uint_16";
                }
                leaf "FwDistRSrc_ItActive" {
                    type "lbox_off_on";
                    default "On";
                }
                leaf "FwDistRSrc_Note" {
                    type "string" {
                        pattern "[^\"`\\\\$;]{0,42}";
                    }
                    default "";
                }
                leaf "FwDistRSrc_RadioAddr" {
                    type "inet:ipv4-address";
                    default "0.0.0.0";
                }
            }
            list "RR_S_TABLE_KrngGenCertSANs" {
                key "ID";
                max-elements "16";
                leaf "ID" {
                    type "lim_uint_16";
                }
                leaf "KrngGCSAN_ItActive" {
                    type "lbox_off_on";
                    default "On";
                }
                leaf "KrngGCSAN_Type" {
                    type "enumeration" {
                        enum "LB_KrngGCSAN_Type_IP" {
                            value "0";
                        }
                        enum "LB_KrngGCSAN_Type_DNS" {
                            value "1";
                        }
                    }
                    default "LB_KrngGCSAN_Type_IP";
                }
                leaf "KrngGCSAN_Note" {
                    type "string" {
                        pattern "[^\"`\\\\$;]{0,42}";
                    }
                    default "";
                }
                leaf "KrngGCSAN_IpAddr" {
                    when "not (../KrngGCSAN_Type != 'LB_KrngGCSAN_Type_IP')";
                    type "inet:ipv4-address";
                    default "0.0.0.0";
                }
                leaf "KrngGCSAN_DnsName" {
                    when "not (../KrngGCSAN_Type != 'LB_KrngGCSAN_Type_DNS')";
                    type "string" {
                        pattern "[a-zA-Z0-9.-]{0,128}";
                    }
                    default "";
                }
            }
            list "RR_S_TABLE_MqttBridgeTopics" {
                when "not ((/config_data/main/MqttBroker/RR_MqttBroker_Enable != 'On') or (/config_data/main/MqttBroker/RR_MqttBroker_BridgeEnable != 'On'))";
                key "ID";
                max-elements "10";
                min-elements "1";
                ordered-by "user";
                leaf "ID" {
                    type "lim_uint_16";
                }
                leaf "MqttBrTopic_ItActive" {
                    type "lbox_off_on";
                    default "On";
                }
                leaf "MqttBrTopic_Direction" {
                    type "lbox_mqtt_direction";
                    default "LB_mqtt_direction_in";
                }
                leaf "MqttBrTopic_QoSLevel" {
                    type "lbox_mqtt_qos";
                    default "LB_mqtt_qos_0";
                }
                leaf "MqttBrTopic_Pattern" {
                    type "string" {
                        pattern "(([a-zA-Z0-9_]+(/([a-zA-Z0-9_]+|[+]))*(/#)?)|[#+])?";
                    }
                    default "";
                }
                leaf "MqttBrTopic_LocalPrefix" {
                    type "string" {
                        pattern "([a-zA-Z0-9_]+(/[a-zA-Z0-9_]+)*/?)?";
                    }
                    default "";
                }
                leaf "MqttBrTopic_RemotePrefix" {
                    type "string" {
                        pattern "([a-zA-Z0-9_]+(/[a-zA-Z0-9_]+)*/?)?";
                    }
                    default "";
                }
                leaf "MqttBrTopic_Note" {
                    type "string" {
                        pattern "[^\"`\\\\$;]{0,42}";
                    }
                    default "";
                }
            }
        }
        container "auth" {
            container "CnfAuth" {
                leaf "RR_CnfAuthCnfVersion" {
                    type "uint16" {
                        range "0..1023";
                    }
                    must ". = 34" {
                        error-message "Wrong configuration version.";
                    }
                    mandatory "true";
                }
            }
        }
        container "monitoring" {
            container "Monitoring" {
                leaf "RR_MoniArchFileMaxSize" {
                    type "enumeration" {
                        enum "1 kB" {
                            value "1";
                        }
                        enum "10 kB" {
                            value "2";
                        }
                        enum "50 kB" {
                            value "3";
                        }
                        enum "100 kB" {
                            value "4";
                        }
                        enum "500 kB" {
                            value "5";
                        }
                        enum "1 MB" {
                            value "6";
                        }
                        enum "max (~2MB)" {
                            value "14";
                        }
                    }
                }
                leaf "RR_MoniArchFileTime" {
                    type "enumeration" {
                        enum "1 min" {
                            value "1";
                        }
                        enum "2 min" {
                            value "2";
                        }
                        enum "5 min" {
                            value "3";
                        }
                        enum "10 min" {
                            value "4";
                        }
                        enum "20 min" {
                            value "5";
                        }
                        enum "30 min" {
                            value "6";
                        }
                        enum "1 hour" {
                            value "7";
                        }
                        enum "3 hours" {
                            value "8";
                        }
                        enum "24 hours" {
                            value "9";
                        }
                        enum "Off" {
                            value "0";
                        }
                    }
                }
                leaf "RR_MoniShowTimeDiff" {
                    type "lbox_off_on";
                }
            }
            container "MonitoringCom1" {
                when "not (/config_data/device/DeviceHw/RR_DynHw_Port_Com1 != 'On')";
                leaf "RR_MoniCom1PhyIfEn" {
                    type "lbox_off_on";
                }
                leaf "RR_MoniCom1PhyIfRxEn" {
                    when "not (/config_data/monitoring/MonitoringCom1/RR_MoniCom1PhyIfEn != 'On')";
                    type "lbox_off_on";
                }
                leaf "RR_MoniCom1PhyIfTxEn" {
                    when "not (/config_data/monitoring/MonitoringCom1/RR_MoniCom1PhyIfEn != 'On')";
                    type "lbox_off_on";
                }
                leaf "RR_MoniCom1IprIfEn" {
                    type "lbox_off_on";
                }
                leaf "RR_MoniCom1IprIfRxEn" {
                    when "not (/config_data/monitoring/MonitoringCom1/RR_MoniCom1IprIfEn != 'On')";
                    type "lbox_off_on";
                }
                leaf "RR_MoniCom1IprIfTxEn" {
                    when "not (/config_data/monitoring/MonitoringCom1/RR_MoniCom1IprIfEn != 'On')";
                    type "lbox_off_on";
                }
                leaf "RR_MoniCom1MonBandwidth" {
                    when "not ((/config_data/monitoring/MonitoringCom1/RR_MoniCom1PhyIfEn != 'On') and (/config_data/monitoring/MonitoringCom1/RR_MoniCom1IprIfEn != 'On'))";
                    type "lbox_moni_max_bandwidth";
                }
            }
            container "MonitoringCom1Phy" {
                when "not ((/config_data/device/DeviceHw/RR_DynHw_Port_Com1 != 'On') or (/config_data/monitoring/MonitoringCom1/RR_MoniCom1PhyIfEn != 'On') or ((/config_data/monitoring/MonitoringCom1/RR_MoniCom1PhyIfRxEn != 'On') and (/config_data/monitoring/MonitoringCom1/RR_MoniCom1PhyIfTxEn != 'On')))";
                leaf "RR_MoniCom1PhyDispFrom" {
                    type "lim_uint_16";
                }
                leaf "RR_MoniCom1PhyDispLen" {
                    type "lim_uint_16";
                }
                leaf "RR_MoniCom1PhyDispDrop" {
                    type "lbox_off_on";
                }
            }
            container "MonitoringCom1Ipr" {
                when "not ((/config_data/device/DeviceHw/RR_DynHw_Port_Com1 != 'On') or (/config_data/monitoring/MonitoringCom1/RR_MoniCom1IprIfEn != 'On') or ((/config_data/monitoring/MonitoringCom1/RR_MoniCom1IprIfRxEn != 'On') and (/config_data/monitoring/MonitoringCom1/RR_MoniCom1IprIfTxEn != 'On')))";
                leaf "RR_MoniCom1IprDispFrom" {
                    type "lim_uint_16";
                }
                leaf "RR_MoniCom1IprDispLen" {
                    type "lim_uint_16";
                }
                leaf "RR_MoniCom1IprIpSrc" {
                    type "inet:ipv4-address";
                }
                leaf "RR_MoniCom1IprIpSrcMask" {
                    type "lim_ipv4_mask0";
                }
                leaf "RR_MoniCom1IprIpDstMask" {
                    type "lim_ipv4_mask0";
                }
                leaf "RR_MoniCom1IprReverse" {
                    type "lbox_off_on";
                }
                leaf "RR_MoniCom1IprDispDrop" {
                    type "lbox_off_on";
                }
                leaf "RR_MoniCom1IprIpDst" {
                    type "inet:ipv4-address";
                }
                leaf "RR_MoniCom1IprPortSrcFrom" {
                    type "lim_udp_port0";
                    must ". <= /config_data/monitoring/MonitoringCom1Ipr/RR_MoniCom1IprPortSrcTo" {
                        error-message "valmsg_it_MoniCom1IprPortSrcFrom";
                    }
                }
                leaf "RR_MoniCom1IprPortSrcTo" {
                    type "lim_udp_port0";
                    must ". >= /config_data/monitoring/MonitoringCom1Ipr/RR_MoniCom1IprPortSrcFrom" {
                        error-message "valmsg_it_MoniCom1IprPortSrcTo";
                    }
                }
                leaf "RR_MoniCom1IprPortDstFrom" {
                    type "lim_udp_port0";
                    must ". <= /config_data/monitoring/MonitoringCom1Ipr/RR_MoniCom1IprPortDstTo" {
                        error-message "valmsg_it_MoniCom1IprPortDstFrom";
                    }
                }
                leaf "RR_MoniCom1IprPortDstTo" {
                    type "lim_udp_port0";
                    must ". >= /config_data/monitoring/MonitoringCom1Ipr/RR_MoniCom1IprPortDstFrom" {
                        error-message "valmsg_it_MoniCom1IprPortDstTo";
                    }
                }
            }
            container "MonitoringCom2" {
                when "not (/config_data/device/DeviceHw/RR_DynHw_Port_Com2 != 'On')";
                leaf "RR_MoniCom2PhyIfEn" {
                    type "lbox_off_on";
                }
                leaf "RR_MoniCom2PhyIfRxEn" {
                    when "not (/config_data/monitoring/MonitoringCom2/RR_MoniCom2PhyIfEn != 'On')";
                    type "lbox_off_on";
                }
                leaf "RR_MoniCom2PhyIfTxEn" {
                    when "not (/config_data/monitoring/MonitoringCom2/RR_MoniCom2PhyIfEn != 'On')";
                    type "lbox_off_on";
                }
                leaf "RR_MoniCom2IprIfEn" {
                    type "lbox_off_on";
                }
                leaf "RR_MoniCom2IprIfRxEn" {
                    when "not (/config_data/monitoring/MonitoringCom2/RR_MoniCom2IprIfEn != 'On')";
                    type "lbox_off_on";
                }
                leaf "RR_MoniCom2IprIfTxEn" {
                    when "not (/config_data/monitoring/MonitoringCom2/RR_MoniCom2IprIfEn != 'On')";
                    type "lbox_off_on";
                }
                leaf "RR_MoniCom2MonBandwidth" {
                    when "not ((/config_data/monitoring/MonitoringCom2/RR_MoniCom2PhyIfEn != 'On') and (/config_data/monitoring/MonitoringCom2/RR_MoniCom2IprIfEn != 'On'))";
                    type "lbox_moni_max_bandwidth";
                }
            }
            container "MonitoringCom2Phy" {
                when "not ((/config_data/device/DeviceHw/RR_DynHw_Port_Com2 != 'On') or (/config_data/monitoring/MonitoringCom2/RR_MoniCom2PhyIfEn != 'On') or ((/config_data/monitoring/MonitoringCom2/RR_MoniCom2PhyIfRxEn != 'On') and (/config_data/monitoring/MonitoringCom2/RR_MoniCom2PhyIfTxEn != 'On')))";
                leaf "RR_MoniCom2PhyDispFrom" {
                    type "lim_uint_16";
                }
                leaf "RR_MoniCom2PhyDispLen" {
                    type "lim_uint_16";
                }
                leaf "RR_MoniCom2PhyDispDrop" {
                    type "lbox_off_on";
                }
            }
            container "MonitoringCom2Ipr" {
                when "not ((/config_data/device/DeviceHw/RR_DynHw_Port_Com2 != 'On') or (/config_data/monitoring/MonitoringCom2/RR_MoniCom2IprIfEn != 'On') or ((/config_data/monitoring/MonitoringCom2/RR_MoniCom2IprIfRxEn != 'On') and (/config_data/monitoring/MonitoringCom2/RR_MoniCom2IprIfTxEn != 'On')))";
                leaf "RR_MoniCom2IprDispFrom" {
                    type "lim_uint_16";
                }
                leaf "RR_MoniCom2IprDispLen" {
                    type "lim_uint_16";
                }
                leaf "RR_MoniCom2IprIpSrc" {
                    type "inet:ipv4-address";
                }
                leaf "RR_MoniCom2IprIpSrcMask" {
                    type "lim_ipv4_mask0";
                }
                leaf "RR_MoniCom2IprIpDstMask" {
                    type "lim_ipv4_mask0";
                }
                leaf "RR_MoniCom2IprReverse" {
                    type "lbox_off_on";
                }
                leaf "RR_MoniCom2IprDispDrop" {
                    type "lbox_off_on";
                }
                leaf "RR_MoniCom2IprIpDst" {
                    type "inet:ipv4-address";
                }
                leaf "RR_MoniCom2IprPortSrcFrom" {
                    type "lim_udp_port0";
                    must ". <= /config_data/monitoring/MonitoringCom2Ipr/RR_MoniCom2IprPortSrcTo" {
                        error-message "valmsg_it_MoniCom2IprPortSrcFrom";
                    }
                }
                leaf "RR_MoniCom2IprPortSrcTo" {
                    type "lim_udp_port0";
                    must ". >= /config_data/monitoring/MonitoringCom2Ipr/RR_MoniCom2IprPortSrcFrom" {
                        error-message "valmsg_it_MoniCom2IprPortSrcTo";
                    }
                }
                leaf "RR_MoniCom2IprPortDstFrom" {
                    type "lim_udp_port0";
                    must ". <= /config_data/monitoring/MonitoringCom2Ipr/RR_MoniCom2IprPortDstTo" {
                        error-message "valmsg_it_MoniCom2IprPortDstFrom";
                    }
                }
                leaf "RR_MoniCom2IprPortDstTo" {
                    type "lim_udp_port0";
                    must ". >= /config_data/monitoring/MonitoringCom2Ipr/RR_MoniCom2IprPortDstFrom" {
                        error-message "valmsg_it_MoniCom2IprPortDstTo";
                    }
                }
            }
            container "MonitoringCom3" {
                when "not (/config_data/device/DeviceHw/RR_DynHw_Port_Com3 != 'On')";
                leaf "RR_MoniCom3PhyIfEn" {
                    type "lbox_off_on";
                }
                leaf "RR_MoniCom3PhyIfRxEn" {
                    when "not (/config_data/monitoring/MonitoringCom3/RR_MoniCom3PhyIfEn != 'On')";
                    type "lbox_off_on";
                }
                leaf "RR_MoniCom3PhyIfTxEn" {
                    when "not (/config_data/monitoring/MonitoringCom3/RR_MoniCom3PhyIfEn != 'On')";
                    type "lbox_off_on";
                }
                leaf "RR_MoniCom3IprIfEn" {
                    type "lbox_off_on";
                }
                leaf "RR_MoniCom3IprIfRxEn" {
                    when "not (/config_data/monitoring/MonitoringCom3/RR_MoniCom3IprIfEn != 'On')";
                    type "lbox_off_on";
                }
                leaf "RR_MoniCom3IprIfTxEn" {
                    when "not (/config_data/monitoring/MonitoringCom3/RR_MoniCom3IprIfEn != 'On')";
                    type "lbox_off_on";
                }
                leaf "RR_MoniCom3MonBandwidth" {
                    when "not ((/config_data/monitoring/MonitoringCom3/RR_MoniCom3PhyIfEn != 'On') and (/config_data/monitoring/MonitoringCom3/RR_MoniCom3IprIfEn != 'On'))";
                    type "lbox_moni_max_bandwidth";
                }
            }
            container "MonitoringCom3Phy" {
                when "not ((/config_data/device/DeviceHw/RR_DynHw_Port_Com3 != 'On') or (/config_data/monitoring/MonitoringCom3/RR_MoniCom3PhyIfEn != 'On') or ((/config_data/monitoring/MonitoringCom3/RR_MoniCom3PhyIfRxEn != 'On') and (/config_data/monitoring/MonitoringCom3/RR_MoniCom3PhyIfTxEn != 'On')))";
                leaf "RR_MoniCom3PhyDispFrom" {
                    type "lim_uint_16";
                }
                leaf "RR_MoniCom3PhyDispLen" {
                    type "lim_uint_16";
                }
                leaf "RR_MoniCom3PhyDispDrop" {
                    type "lbox_off_on";
                }
            }
            container "MonitoringCom3Ipr" {
                when "not ((/config_data/device/DeviceHw/RR_DynHw_Port_Com3 != 'On') or (/config_data/monitoring/MonitoringCom3/RR_MoniCom3IprIfEn != 'On') or ((/config_data/monitoring/MonitoringCom3/RR_MoniCom3IprIfRxEn != 'On') and (/config_data/monitoring/MonitoringCom3/RR_MoniCom3IprIfTxEn != 'On')))";
                leaf "RR_MoniCom3IprDispFrom" {
                    type "lim_uint_16";
                }
                leaf "RR_MoniCom3IprDispLen" {
                    type "lim_uint_16";
                }
                leaf "RR_MoniCom3IprIpSrc" {
                    type "inet:ipv4-address";
                }
                leaf "RR_MoniCom3IprIpSrcMask" {
                    type "lim_ipv4_mask0";
                }
                leaf "RR_MoniCom3IprIpDstMask" {
                    type "lim_ipv4_mask0";
                }
                leaf "RR_MoniCom3IprReverse" {
                    type "lbox_off_on";
                }
                leaf "RR_MoniCom3IprDispDrop" {
                    type "lbox_off_on";
                }
                leaf "RR_MoniCom3IprIpDst" {
                    type "inet:ipv4-address";
                }
                leaf "RR_MoniCom3IprPortSrcFrom" {
                    type "lim_udp_port0";
                    must ". <= /config_data/monitoring/MonitoringCom3Ipr/RR_MoniCom3IprPortSrcTo" {
                        error-message "valmsg_it_MoniCom3IprPortSrcFrom";
                    }
                }
                leaf "RR_MoniCom3IprPortSrcTo" {
                    type "lim_udp_port0";
                    must ". >= /config_data/monitoring/MonitoringCom3Ipr/RR_MoniCom3IprPortSrcFrom" {
                        error-message "valmsg_it_MoniCom3IprPortSrcTo";
                    }
                }
                leaf "RR_MoniCom3IprPortDstFrom" {
                    type "lim_udp_port0";
                    must ". <= /config_data/monitoring/MonitoringCom3Ipr/RR_MoniCom3IprPortDstTo" {
                        error-message "valmsg_it_MoniCom3IprPortDstFrom";
                    }
                }
                leaf "RR_MoniCom3IprPortDstTo" {
                    type "lim_udp_port0";
                    must ". >= /config_data/monitoring/MonitoringCom3Ipr/RR_MoniCom3IprPortDstFrom" {
                        error-message "valmsg_it_MoniCom3IprPortDstTo";
                    }
                }
            }
            container "MonitoringTS1" {
                leaf "RR_MoniTS1PhyIfEn" {
                    type "lbox_off_on";
                }
                leaf "RR_MoniTS1PhyIfRxEn" {
                    when "not (/config_data/monitoring/MonitoringTS1/RR_MoniTS1PhyIfEn != 'On')";
                    type "lbox_off_on";
                }
                leaf "RR_MoniTS1PhyIfTxEn" {
                    when "not (/config_data/monitoring/MonitoringTS1/RR_MoniTS1PhyIfEn != 'On')";
                    type "lbox_off_on";
                }
                leaf "RR_MoniTS1IprIfEn" {
                    type "lbox_off_on";
                }
                leaf "RR_MoniTS1IprIfRxEn" {
                    when "not (/config_data/monitoring/MonitoringTS1/RR_MoniTS1IprIfEn != 'On')";
                    type "lbox_off_on";
                }
                leaf "RR_MoniTS1IprIfTxEn" {
                    when "not (/config_data/monitoring/MonitoringTS1/RR_MoniTS1IprIfEn != 'On')";
                    type "lbox_off_on";
                }
                leaf "RR_MoniTS1MonBandwidth" {
                    when "not ((/config_data/monitoring/MonitoringTS1/RR_MoniTS1PhyIfEn != 'On') and (/config_data/monitoring/MonitoringTS1/RR_MoniTS1IprIfEn != 'On'))";
                    type "lbox_moni_max_bandwidth";
                }
            }
            container "MonitoringTS1Phy" {
                when "not ((/config_data/monitoring/MonitoringTS1/RR_MoniTS1PhyIfEn != 'On') or ((/config_data/monitoring/MonitoringTS1/RR_MoniTS1PhyIfRxEn != 'On') and (/config_data/monitoring/MonitoringTS1/RR_MoniTS1PhyIfTxEn != 'On')))";
                leaf "RR_MoniTS1PhyDispFrom" {
                    type "lim_uint_16";
                }
                leaf "RR_MoniTS1PhyDispLen" {
                    type "lim_uint_16";
                }
                leaf "RR_MoniTS1PhyDispDrop" {
                    type "lbox_off_on";
                }
            }
            container "MonitoringTS1Ipr" {
                when "not ((/config_data/monitoring/MonitoringTS1/RR_MoniTS1IprIfEn != 'On') or ((/config_data/monitoring/MonitoringTS1/RR_MoniTS1IprIfRxEn != 'On') and (/config_data/monitoring/MonitoringTS1/RR_MoniTS1IprIfTxEn != 'On')))";
                leaf "RR_MoniTS1IprDispFrom" {
                    type "lim_uint_16";
                }
                leaf "RR_MoniTS1IprDispLen" {
                    type "lim_uint_16";
                }
                leaf "RR_MoniTS1IprIpSrc" {
                    type "inet:ipv4-address";
                }
                leaf "RR_MoniTS1IprIpSrcMask" {
                    type "lim_ipv4_mask0";
                }
                leaf "RR_MoniTS1IprIpDstMask" {
                    type "lim_ipv4_mask0";
                }
                leaf "RR_MoniTS1IprReverse" {
                    type "lbox_off_on";
                }
                leaf "RR_MoniTS1IprDispDrop" {
                    type "lbox_off_on";
                }
                leaf "RR_MoniTS1IprIpDst" {
                    type "inet:ipv4-address";
                }
                leaf "RR_MoniTS1IprPortSrcFrom" {
                    type "lim_udp_port0";
                    must ". <= /config_data/monitoring/MonitoringTS1Ipr/RR_MoniTS1IprPortSrcTo" {
                        error-message "valmsg_it_MoniTS1IprPortSrcFrom";
                    }
                }
                leaf "RR_MoniTS1IprPortSrcTo" {
                    type "lim_udp_port0";
                    must ". >= /config_data/monitoring/MonitoringTS1Ipr/RR_MoniTS1IprPortSrcFrom" {
                        error-message "valmsg_it_MoniTS1IprPortSrcTo";
                    }
                }
                leaf "RR_MoniTS1IprPortDstFrom" {
                    type "lim_udp_port0";
                    must ". <= /config_data/monitoring/MonitoringTS1Ipr/RR_MoniTS1IprPortDstTo" {
                        error-message "valmsg_it_MoniTS1IprPortDstFrom";
                    }
                }
                leaf "RR_MoniTS1IprPortDstTo" {
                    type "lim_udp_port0";
                    must ". >= /config_data/monitoring/MonitoringTS1Ipr/RR_MoniTS1IprPortDstFrom" {
                        error-message "valmsg_it_MoniTS1IprPortDstTo";
                    }
                }
            }
            container "MonitoringTS2" {
                leaf "RR_MoniTS2PhyIfEn" {
                    type "lbox_off_on";
                }
                leaf "RR_MoniTS2PhyIfRxEn" {
                    when "not (/config_data/monitoring/MonitoringTS2/RR_MoniTS2PhyIfEn != 'On')";
                    type "lbox_off_on";
                }
                leaf "RR_MoniTS2PhyIfTxEn" {
                    when "not (/config_data/monitoring/MonitoringTS2/RR_MoniTS2PhyIfEn != 'On')";
                    type "lbox_off_on";
                }
                leaf "RR_MoniTS2IprIfEn" {
                    type "lbox_off_on";
                }
                leaf "RR_MoniTS2IprIfRxEn" {
                    when "not (/config_data/monitoring/MonitoringTS2/RR_MoniTS2IprIfEn != 'On')";
                    type "lbox_off_on";
                }
                leaf "RR_MoniTS2IprIfTxEn" {
                    when "not (/config_data/monitoring/MonitoringTS2/RR_MoniTS2IprIfEn != 'On')";
                    type "lbox_off_on";
                }
                leaf "RR_MoniTS2MonBandwidth" {
                    when "not ((/config_data/monitoring/MonitoringTS2/RR_MoniTS2PhyIfEn != 'On') and (/config_data/monitoring/MonitoringTS2/RR_MoniTS2IprIfEn != 'On'))";
                    type "lbox_moni_max_bandwidth";
                }
            }
            container "MonitoringTS2Phy" {
                when "not ((/config_data/monitoring/MonitoringTS2/RR_MoniTS2PhyIfEn != 'On') or ((/config_data/monitoring/MonitoringTS2/RR_MoniTS2PhyIfRxEn != 'On') and (/config_data/monitoring/MonitoringTS2/RR_MoniTS2PhyIfTxEn != 'On')))";
                leaf "RR_MoniTS2PhyDispFrom" {
                    type "lim_uint_16";
                }
                leaf "RR_MoniTS2PhyDispLen" {
                    type "lim_uint_16";
                }
                leaf "RR_MoniTS2PhyDispDrop" {
                    type "lbox_off_on";
                }
            }
            container "MonitoringTS2Ipr" {
                when "not ((/config_data/monitoring/MonitoringTS2/RR_MoniTS2IprIfEn != 'On') or ((/config_data/monitoring/MonitoringTS2/RR_MoniTS2IprIfRxEn != 'On') and (/config_data/monitoring/MonitoringTS2/RR_MoniTS2IprIfTxEn != 'On')))";
                leaf "RR_MoniTS2IprDispFrom" {
                    type "lim_uint_16";
                }
                leaf "RR_MoniTS2IprDispLen" {
                    type "lim_uint_16";
                }
                leaf "RR_MoniTS2IprIpSrc" {
                    type "inet:ipv4-address";
                }
                leaf "RR_MoniTS2IprIpSrcMask" {
                    type "lim_ipv4_mask0";
                }
                leaf "RR_MoniTS2IprIpDstMask" {
                    type "lim_ipv4_mask0";
                }
                leaf "RR_MoniTS2IprReverse" {
                    type "lbox_off_on";
                }
                leaf "RR_MoniTS2IprDispDrop" {
                    type "lbox_off_on";
                }
                leaf "RR_MoniTS2IprIpDst" {
                    type "inet:ipv4-address";
                }
                leaf "RR_MoniTS2IprPortSrcFrom" {
                    type "lim_udp_port0";
                    must ". <= /config_data/monitoring/MonitoringTS2Ipr/RR_MoniTS2IprPortSrcTo" {
                        error-message "valmsg_it_MoniTS2IprPortSrcFrom";
                    }
                }
                leaf "RR_MoniTS2IprPortSrcTo" {
                    type "lim_udp_port0";
                    must ". >= /config_data/monitoring/MonitoringTS2Ipr/RR_MoniTS2IprPortSrcFrom" {
                        error-message "valmsg_it_MoniTS2IprPortSrcTo";
                    }
                }
                leaf "RR_MoniTS2IprPortDstFrom" {
                    type "lim_udp_port0";
                    must ". <= /config_data/monitoring/MonitoringTS2Ipr/RR_MoniTS2IprPortDstTo" {
                        error-message "valmsg_it_MoniTS2IprPortDstFrom";
                    }
                }
                leaf "RR_MoniTS2IprPortDstTo" {
                    type "lim_udp_port0";
                    must ". >= /config_data/monitoring/MonitoringTS2Ipr/RR_MoniTS2IprPortDstFrom" {
                        error-message "valmsg_it_MoniTS2IprPortDstTo";
                    }
                }
            }
            container "MonitoringTS3" {
                leaf "RR_MoniTS3PhyIfEn" {
                    type "lbox_off_on";
                }
                leaf "RR_MoniTS3PhyIfRxEn" {
                    when "not (/config_data/monitoring/MonitoringTS3/RR_MoniTS3PhyIfEn != 'On')";
                    type "lbox_off_on";
                }
                leaf "RR_MoniTS3PhyIfTxEn" {
                    when "not (/config_data/monitoring/MonitoringTS3/RR_MoniTS3PhyIfEn != 'On')";
                    type "lbox_off_on";
                }
                leaf "RR_MoniTS3IprIfEn" {
                    type "lbox_off_on";
                }
                leaf "RR_MoniTS3IprIfRxEn" {
                    when "not (/config_data/monitoring/MonitoringTS3/RR_MoniTS3IprIfEn != 'On')";
                    type "lbox_off_on";
                }
                leaf "RR_MoniTS3IprIfTxEn" {
                    when "not (/config_data/monitoring/MonitoringTS3/RR_MoniTS3IprIfEn != 'On')";
                    type "lbox_off_on";
                }
                leaf "RR_MoniTS3MonBandwidth" {
                    when "not ((/config_data/monitoring/MonitoringTS3/RR_MoniTS3PhyIfEn != 'On') and (/config_data/monitoring/MonitoringTS3/RR_MoniTS3IprIfEn != 'On'))";
                    type "lbox_moni_max_bandwidth";
                }
            }
            container "MonitoringTS3Phy" {
                when "not ((/config_data/monitoring/MonitoringTS3/RR_MoniTS3PhyIfEn != 'On') or ((/config_data/monitoring/MonitoringTS3/RR_MoniTS3PhyIfRxEn != 'On') and (/config_data/monitoring/MonitoringTS3/RR_MoniTS3PhyIfTxEn != 'On')))";
                leaf "RR_MoniTS3PhyDispFrom" {
                    type "lim_uint_16";
                }
                leaf "RR_MoniTS3PhyDispLen" {
                    type "lim_uint_16";
                }
                leaf "RR_MoniTS3PhyDispDrop" {
                    type "lbox_off_on";
                }
            }
            container "MonitoringTS3Ipr" {
                when "not ((/config_data/monitoring/MonitoringTS3/RR_MoniTS3IprIfEn != 'On') or ((/config_data/monitoring/MonitoringTS3/RR_MoniTS3IprIfRxEn != 'On') and (/config_data/monitoring/MonitoringTS3/RR_MoniTS3IprIfTxEn != 'On')))";
                leaf "RR_MoniTS3IprDispFrom" {
                    type "lim_uint_16";
                }
                leaf "RR_MoniTS3IprDispLen" {
                    type "lim_uint_16";
                }
                leaf "RR_MoniTS3IprIpSrc" {
                    type "inet:ipv4-address";
                }
                leaf "RR_MoniTS3IprIpSrcMask" {
                    type "lim_ipv4_mask0";
                }
                leaf "RR_MoniTS3IprIpDstMask" {
                    type "lim_ipv4_mask0";
                }
                leaf "RR_MoniTS3IprReverse" {
                    type "lbox_off_on";
                }
                leaf "RR_MoniTS3IprDispDrop" {
                    type "lbox_off_on";
                }
                leaf "RR_MoniTS3IprIpDst" {
                    type "inet:ipv4-address";
                }
                leaf "RR_MoniTS3IprPortSrcFrom" {
                    type "lim_udp_port0";
                    must ". <= /config_data/monitoring/MonitoringTS3Ipr/RR_MoniTS3IprPortSrcTo" {
                        error-message "valmsg_it_MoniTS3IprPortSrcFrom";
                    }
                }
                leaf "RR_MoniTS3IprPortSrcTo" {
                    type "lim_udp_port0";
                    must ". >= /config_data/monitoring/MonitoringTS3Ipr/RR_MoniTS3IprPortSrcFrom" {
                        error-message "valmsg_it_MoniTS3IprPortSrcTo";
                    }
                }
                leaf "RR_MoniTS3IprPortDstFrom" {
                    type "lim_udp_port0";
                    must ". <= /config_data/monitoring/MonitoringTS3Ipr/RR_MoniTS3IprPortDstTo" {
                        error-message "valmsg_it_MoniTS3IprPortDstFrom";
                    }
                }
                leaf "RR_MoniTS3IprPortDstTo" {
                    type "lim_udp_port0";
                    must ". >= /config_data/monitoring/MonitoringTS3Ipr/RR_MoniTS3IprPortDstFrom" {
                        error-message "valmsg_it_MoniTS3IprPortDstTo";
                    }
                }
            }
            container "MonitoringTS4" {
                leaf "RR_MoniTS4PhyIfEn" {
                    type "lbox_off_on";
                }
                leaf "RR_MoniTS4PhyIfRxEn" {
                    when "not (/config_data/monitoring/MonitoringTS4/RR_MoniTS4PhyIfEn != 'On')";
                    type "lbox_off_on";
                }
                leaf "RR_MoniTS4PhyIfTxEn" {
                    when "not (/config_data/monitoring/MonitoringTS4/RR_MoniTS4PhyIfEn != 'On')";
                    type "lbox_off_on";
                }
                leaf "RR_MoniTS4IprIfEn" {
                    type "lbox_off_on";
                }
                leaf "RR_MoniTS4IprIfRxEn" {
                    when "not (/config_data/monitoring/MonitoringTS4/RR_MoniTS4IprIfEn != 'On')";
                    type "lbox_off_on";
                }
                leaf "RR_MoniTS4IprIfTxEn" {
                    when "not (/config_data/monitoring/MonitoringTS4/RR_MoniTS4IprIfEn != 'On')";
                    type "lbox_off_on";
                }
                leaf "RR_MoniTS4MonBandwidth" {
                    when "not ((/config_data/monitoring/MonitoringTS4/RR_MoniTS4PhyIfEn != 'On') and (/config_data/monitoring/MonitoringTS4/RR_MoniTS4IprIfEn != 'On'))";
                    type "lbox_moni_max_bandwidth";
                }
            }
            container "MonitoringTS4Phy" {
                when "not ((/config_data/monitoring/MonitoringTS4/RR_MoniTS4PhyIfEn != 'On') or ((/config_data/monitoring/MonitoringTS4/RR_MoniTS4PhyIfRxEn != 'On') and (/config_data/monitoring/MonitoringTS4/RR_MoniTS4PhyIfTxEn != 'On')))";
                leaf "RR_MoniTS4PhyDispFrom" {
                    type "lim_uint_16";
                }
                leaf "RR_MoniTS4PhyDispLen" {
                    type "lim_uint_16";
                }
                leaf "RR_MoniTS4PhyDispDrop" {
                    type "lbox_off_on";
                }
            }
            container "MonitoringTS4Ipr" {
                when "not ((/config_data/monitoring/MonitoringTS4/RR_MoniTS4IprIfEn != 'On') or ((/config_data/monitoring/MonitoringTS4/RR_MoniTS4IprIfRxEn != 'On') and (/config_data/monitoring/MonitoringTS4/RR_MoniTS4IprIfTxEn != 'On')))";
                leaf "RR_MoniTS4IprDispFrom" {
                    type "lim_uint_16";
                }
                leaf "RR_MoniTS4IprDispLen" {
                    type "lim_uint_16";
                }
                leaf "RR_MoniTS4IprIpSrc" {
                    type "inet:ipv4-address";
                }
                leaf "RR_MoniTS4IprIpSrcMask" {
                    type "lim_ipv4_mask0";
                }
                leaf "RR_MoniTS4IprIpDstMask" {
                    type "lim_ipv4_mask0";
                }
                leaf "RR_MoniTS4IprReverse" {
                    type "lbox_off_on";
                }
                leaf "RR_MoniTS4IprDispDrop" {
                    type "lbox_off_on";
                }
                leaf "RR_MoniTS4IprIpDst" {
                    type "inet:ipv4-address";
                }
                leaf "RR_MoniTS4IprPortSrcFrom" {
                    type "lim_udp_port0";
                    must ". <= /config_data/monitoring/MonitoringTS4Ipr/RR_MoniTS4IprPortSrcTo" {
                        error-message "valmsg_it_MoniTS4IprPortSrcFrom";
                    }
                }
                leaf "RR_MoniTS4IprPortSrcTo" {
                    type "lim_udp_port0";
                    must ". >= /config_data/monitoring/MonitoringTS4Ipr/RR_MoniTS4IprPortSrcFrom" {
                        error-message "valmsg_it_MoniTS4IprPortSrcTo";
                    }
                }
                leaf "RR_MoniTS4IprPortDstFrom" {
                    type "lim_udp_port0";
                    must ". <= /config_data/monitoring/MonitoringTS4Ipr/RR_MoniTS4IprPortDstTo" {
                        error-message "valmsg_it_MoniTS4IprPortDstFrom";
                    }
                }
                leaf "RR_MoniTS4IprPortDstTo" {
                    type "lim_udp_port0";
                    must ". >= /config_data/monitoring/MonitoringTS4Ipr/RR_MoniTS4IprPortDstFrom" {
                        error-message "valmsg_it_MoniTS4IprPortDstTo";
                    }
                }
            }
            container "MonitoringTS5" {
                leaf "RR_MoniTS5PhyIfEn" {
                    type "lbox_off_on";
                }
                leaf "RR_MoniTS5PhyIfRxEn" {
                    when "not (/config_data/monitoring/MonitoringTS5/RR_MoniTS5PhyIfEn != 'On')";
                    type "lbox_off_on";
                }
                leaf "RR_MoniTS5PhyIfTxEn" {
                    when "not (/config_data/monitoring/MonitoringTS5/RR_MoniTS5PhyIfEn != 'On')";
                    type "lbox_off_on";
                }
                leaf "RR_MoniTS5IprIfEn" {
                    type "lbox_off_on";
                }
                leaf "RR_MoniTS5IprIfRxEn" {
                    when "not (/config_data/monitoring/MonitoringTS5/RR_MoniTS5IprIfEn != 'On')";
                    type "lbox_off_on";
                }
                leaf "RR_MoniTS5IprIfTxEn" {
                    when "not (/config_data/monitoring/MonitoringTS5/RR_MoniTS5IprIfEn != 'On')";
                    type "lbox_off_on";
                }
                leaf "RR_MoniTS5MonBandwidth" {
                    when "not ((/config_data/monitoring/MonitoringTS5/RR_MoniTS5PhyIfEn != 'On') and (/config_data/monitoring/MonitoringTS5/RR_MoniTS5IprIfEn != 'On'))";
                    type "lbox_moni_max_bandwidth";
                }
            }
            container "MonitoringTS5Phy" {
                when "not ((/config_data/monitoring/MonitoringTS5/RR_MoniTS5PhyIfEn != 'On') or ((/config_data/monitoring/MonitoringTS5/RR_MoniTS5PhyIfRxEn != 'On') and (/config_data/monitoring/MonitoringTS5/RR_MoniTS5PhyIfTxEn != 'On')))";
                leaf "RR_MoniTS5PhyDispFrom" {
                    type "lim_uint_16";
                }
                leaf "RR_MoniTS5PhyDispLen" {
                    type "lim_uint_16";
                }
                leaf "RR_MoniTS5PhyDispDrop" {
                    type "lbox_off_on";
                }
            }
            container "MonitoringTS5Ipr" {
                when "not ((/config_data/monitoring/MonitoringTS5/RR_MoniTS5IprIfEn != 'On') or ((/config_data/monitoring/MonitoringTS5/RR_MoniTS5IprIfRxEn != 'On') and (/config_data/monitoring/MonitoringTS5/RR_MoniTS5IprIfTxEn != 'On')))";
                leaf "RR_MoniTS5IprDispFrom" {
                    type "lim_uint_16";
                }
                leaf "RR_MoniTS5IprDispLen" {
                    type "lim_uint_16";
                }
                leaf "RR_MoniTS5IprIpSrc" {
                    type "inet:ipv4-address";
                }
                leaf "RR_MoniTS5IprIpSrcMask" {
                    type "lim_ipv4_mask0";
                }
                leaf "RR_MoniTS5IprIpDstMask" {
                    type "lim_ipv4_mask0";
                }
                leaf "RR_MoniTS5IprReverse" {
                    type "lbox_off_on";
                }
                leaf "RR_MoniTS5IprDispDrop" {
                    type "lbox_off_on";
                }
                leaf "RR_MoniTS5IprIpDst" {
                    type "inet:ipv4-address";
                }
                leaf "RR_MoniTS5IprPortSrcFrom" {
                    type "lim_udp_port0";
                    must ". <= /config_data/monitoring/MonitoringTS5Ipr/RR_MoniTS5IprPortSrcTo" {
                        error-message "valmsg_it_MoniTS5IprPortSrcFrom";
                    }
                }
                leaf "RR_MoniTS5IprPortSrcTo" {
                    type "lim_udp_port0";
                    must ". >= /config_data/monitoring/MonitoringTS5Ipr/RR_MoniTS5IprPortSrcFrom" {
                        error-message "valmsg_it_MoniTS5IprPortSrcTo";
                    }
                }
                leaf "RR_MoniTS5IprPortDstFrom" {
                    type "lim_udp_port0";
                    must ". <= /config_data/monitoring/MonitoringTS5Ipr/RR_MoniTS5IprPortDstTo" {
                        error-message "valmsg_it_MoniTS5IprPortDstFrom";
                    }
                }
                leaf "RR_MoniTS5IprPortDstTo" {
                    type "lim_udp_port0";
                    must ". >= /config_data/monitoring/MonitoringTS5Ipr/RR_MoniTS5IprPortDstFrom" {
                        error-message "valmsg_it_MoniTS5IprPortDstTo";
                    }
                }
            }
            container "MonitoringLan1" {
                when "not (/config_data/device/DeviceHw/RR_DynHw_Port_Eth_Cnt <= 0)";
                leaf "RR_MoniLan1PhyIfEnabled" {
                    type "lbox_off_on";
                }
                leaf "RR_MoniLan1PhyRxEn" {
                    when "not (/config_data/monitoring/MonitoringLan1/RR_MoniLan1PhyIfEnabled != 'On')";
                    type "lbox_off_on";
                }
                leaf "RR_MoniLan1PhyTxEn" {
                    when "not (/config_data/monitoring/MonitoringLan1/RR_MoniLan1PhyIfEnabled != 'On')";
                    type "lbox_off_on";
                }
                leaf "RR_MoniLan1MonBandwidth" {
                    when "not (/config_data/monitoring/MonitoringLan1/RR_MoniLan1PhyIfEnabled != 'On')";
                    type "lbox_moni_max_bandwidth";
                }
            }
            container "MonitoringLan1Phy" {
                when "not ((/config_data/device/DeviceHw/RR_DynHw_Port_Eth_Cnt <= 0) or (/config_data/monitoring/MonitoringLan1/RR_MoniLan1PhyIfEnabled != 'On') or ((/config_data/monitoring/MonitoringLan1/RR_MoniLan1PhyRxEn != 'On') and (/config_data/monitoring/MonitoringLan1/RR_MoniLan1PhyTxEn != 'On')))";
                leaf "RR_MoniLan1PhyDispFrom" {
                    when "not (/config_data/monitoring/MonitoringLan1Phy/RR_MoniLan1PhyDispHeads = 'On')";
                    type "lim_uint_16";
                }
                leaf "RR_MoniLan1PhyDispLen" {
                    type "lim_uint_16";
                }
                leaf "RR_MoniLan1PhyDispHeads" {
                    type "lbox_off_on";
                }
                leaf "RR_MoniLan1PhyShowMTraffic" {
                    type "lbox_off_on";
                }
                leaf "RR_MoniLan1PhyPackType_All" {
                    type "lbox_off_on";
                }
                leaf "RR_MoniLan1PhyPackType_Udp" {
                    when "not (/config_data/monitoring/MonitoringLan1Phy/RR_MoniLan1PhyPackType_All = 'On')";
                    type "lbox_off_on";
                }
                leaf "RR_MoniLan1PhyPackType_Tcp" {
                    when "not (/config_data/monitoring/MonitoringLan1Phy/RR_MoniLan1PhyPackType_All = 'On')";
                    type "lbox_off_on";
                }
                leaf "RR_MoniLan1PhyPackType_Icmp" {
                    when "not (/config_data/monitoring/MonitoringLan1Phy/RR_MoniLan1PhyPackType_All = 'On')";
                    type "lbox_off_on";
                }
                leaf "RR_MoniLan1PhyPackType_Other" {
                    when "not (/config_data/monitoring/MonitoringLan1Phy/RR_MoniLan1PhyPackType_All = 'On')";
                    type "lbox_off_on";
                }
                leaf "RR_MoniLan1PhyPackType_Arp" {
                    when "not (/config_data/monitoring/MonitoringLan1Phy/RR_MoniLan1PhyPackType_All = 'On')";
                    type "lbox_off_on";
                }
                leaf "RR_MoniLan1PhyIpSrcMask" {
                    type "lim_ipv4_mask0";
                }
                leaf "RR_MoniLan1PhyIpSrc" {
                    type "inet:ipv4-address";
                }
                leaf "RR_MoniLan1PhyIpDst" {
                    type "inet:ipv4-address";
                }
                leaf "RR_MoniLan1PhyIpDstMask" {
                    type "lim_ipv4_mask0";
                }
                leaf "RR_MoniLan1PhyReverse" {
                    type "lbox_off_on";
                }
                leaf "RR_MoniLan1PhyPortSrcFrom" {
                    when "not ((/config_data/monitoring/MonitoringLan1Phy/RR_MoniLan1PhyPackType_All != 'On') and (/config_data/monitoring/MonitoringLan1Phy/RR_MoniLan1PhyPackType_Udp != 'On') and (/config_data/monitoring/MonitoringLan1Phy/RR_MoniLan1PhyPackType_Tcp != 'On'))";
                    type "lim_udp_port0";
                    must ". <= /config_data/monitoring/MonitoringLan1Phy/RR_MoniLan1PhyPortSrcTo" {
                        error-message "valmsg_it_MoniLan1PhyPortSrcFrom";
                    }
                }
                leaf "RR_MoniLan1PhyPortSrcTo" {
                    when "not ((/config_data/monitoring/MonitoringLan1Phy/RR_MoniLan1PhyPackType_All != 'On') and (/config_data/monitoring/MonitoringLan1Phy/RR_MoniLan1PhyPackType_Udp != 'On') and (/config_data/monitoring/MonitoringLan1Phy/RR_MoniLan1PhyPackType_Tcp != 'On'))";
                    type "lim_udp_port0";
                    must ". >= /config_data/monitoring/MonitoringLan1Phy/RR_MoniLan1PhyPortSrcFrom" {
                        error-message "valmsg_it_MoniLan1PhyPortSrcTo";
                    }
                }
                leaf "RR_MoniLan1PhyPortDstFrom" {
                    when "not ((/config_data/monitoring/MonitoringLan1Phy/RR_MoniLan1PhyPackType_All != 'On') and (/config_data/monitoring/MonitoringLan1Phy/RR_MoniLan1PhyPackType_Udp != 'On') and (/config_data/monitoring/MonitoringLan1Phy/RR_MoniLan1PhyPackType_Tcp != 'On'))";
                    type "lim_udp_port0";
                    must ". <= /config_data/monitoring/MonitoringLan1Phy/RR_MoniLan1PhyPortDstTo" {
                        error-message "valmsg_it_MoniLan1PhyPortDstFrom";
                    }
                }
                leaf "RR_MoniLan1PhyPortDstTo" {
                    when "not ((/config_data/monitoring/MonitoringLan1Phy/RR_MoniLan1PhyPackType_All != 'On') and (/config_data/monitoring/MonitoringLan1Phy/RR_MoniLan1PhyPackType_Udp != 'On') and (/config_data/monitoring/MonitoringLan1Phy/RR_MoniLan1PhyPackType_Tcp != 'On'))";
                    type "lim_udp_port0";
                    must ". >= /config_data/monitoring/MonitoringLan1Phy/RR_MoniLan1PhyPortDstFrom" {
                        error-message "valmsg_it_MoniLan1PhyPortDstTo";
                    }
                }
            }
            container "MonitoringLan2" {
                when "not (/config_data/device/DeviceHw/RR_DynHw_Port_Eth_Cnt <= 1)";
                leaf "RR_MoniLan2PhyIfEnabled" {
                    type "lbox_off_on";
                }
                leaf "RR_MoniLan2PhyRxEn" {
                    when "not (/config_data/monitoring/MonitoringLan2/RR_MoniLan2PhyIfEnabled != 'On')";
                    type "lbox_off_on";
                }
                leaf "RR_MoniLan2PhyTxEn" {
                    when "not (/config_data/monitoring/MonitoringLan2/RR_MoniLan2PhyIfEnabled != 'On')";
                    type "lbox_off_on";
                }
                leaf "RR_MoniLan2MonBandwidth" {
                    when "not (/config_data/monitoring/MonitoringLan2/RR_MoniLan2PhyIfEnabled != 'On')";
                    type "lbox_moni_max_bandwidth";
                }
            }
            container "MonitoringLan2Phy" {
                when "not ((/config_data/device/DeviceHw/RR_DynHw_Port_Eth_Cnt <= 1) or (/config_data/monitoring/MonitoringLan2/RR_MoniLan2PhyIfEnabled != 'On') or ((/config_data/monitoring/MonitoringLan2/RR_MoniLan2PhyRxEn != 'On') and (/config_data/monitoring/MonitoringLan2/RR_MoniLan2PhyTxEn != 'On')))";
                leaf "RR_MoniLan2PhyDispFrom" {
                    when "not (/config_data/monitoring/MonitoringLan2Phy/RR_MoniLan2PhyDispHeads = 'On')";
                    type "lim_uint_16";
                }
                leaf "RR_MoniLan2PhyDispLen" {
                    type "lim_uint_16";
                }
                leaf "RR_MoniLan2PhyDispHeads" {
                    type "lbox_off_on";
                }
                leaf "RR_MoniLan2PhyShowMTraffic" {
                    type "lbox_off_on";
                }
                leaf "RR_MoniLan2PhyPackType_All" {
                    type "lbox_off_on";
                }
                leaf "RR_MoniLan2PhyPackType_Udp" {
                    when "not (/config_data/monitoring/MonitoringLan2Phy/RR_MoniLan2PhyPackType_All = 'On')";
                    type "lbox_off_on";
                }
                leaf "RR_MoniLan2PhyPackType_Tcp" {
                    when "not (/config_data/monitoring/MonitoringLan2Phy/RR_MoniLan2PhyPackType_All = 'On')";
                    type "lbox_off_on";
                }
                leaf "RR_MoniLan2PhyPackType_Icmp" {
                    when "not (/config_data/monitoring/MonitoringLan2Phy/RR_MoniLan2PhyPackType_All = 'On')";
                    type "lbox_off_on";
                }
                leaf "RR_MoniLan2PhyPackType_Other" {
                    when "not (/config_data/monitoring/MonitoringLan2Phy/RR_MoniLan2PhyPackType_All = 'On')";
                    type "lbox_off_on";
                }
                leaf "RR_MoniLan2PhyPackType_Arp" {
                    when "not (/config_data/monitoring/MonitoringLan2Phy/RR_MoniLan2PhyPackType_All = 'On')";
                    type "lbox_off_on";
                }
                leaf "RR_MoniLan2PhyIpSrcMask" {
                    type "lim_ipv4_mask0";
                }
                leaf "RR_MoniLan2PhyIpSrc" {
                    type "inet:ipv4-address";
                }
                leaf "RR_MoniLan2PhyIpDst" {
                    type "inet:ipv4-address";
                }
                leaf "RR_MoniLan2PhyIpDstMask" {
                    type "lim_ipv4_mask0";
                }
                leaf "RR_MoniLan2PhyReverse" {
                    type "lbox_off_on";
                }
                leaf "RR_MoniLan2PhyPortSrcFrom" {
                    when "not ((/config_data/monitoring/MonitoringLan2Phy/RR_MoniLan2PhyPackType_All != 'On') and (/config_data/monitoring/MonitoringLan2Phy/RR_MoniLan2PhyPackType_Udp != 'On') and (/config_data/monitoring/MonitoringLan2Phy/RR_MoniLan2PhyPackType_Tcp != 'On'))";
                    type "lim_udp_port0";
                    must ". <= /config_data/monitoring/MonitoringLan2Phy/RR_MoniLan2PhyPortSrcTo" {
                        error-message "valmsg_it_MoniLan2PhyPortSrcFrom";
                    }
                }
                leaf "RR_MoniLan2PhyPortSrcTo" {
                    when "not ((/config_data/monitoring/MonitoringLan2Phy/RR_MoniLan2PhyPackType_All != 'On') and (/config_data/monitoring/MonitoringLan2Phy/RR_MoniLan2PhyPackType_Udp != 'On') and (/config_data/monitoring/MonitoringLan2Phy/RR_MoniLan2PhyPackType_Tcp != 'On'))";
                    type "lim_udp_port0";
                    must ". >= /config_data/monitoring/MonitoringLan2Phy/RR_MoniLan2PhyPortSrcFrom" {
                        error-message "valmsg_it_MoniLan2PhyPortSrcTo";
                    }
                }
                leaf "RR_MoniLan2PhyPortDstFrom" {
                    when "not ((/config_data/monitoring/MonitoringLan2Phy/RR_MoniLan2PhyPackType_All != 'On') and (/config_data/monitoring/MonitoringLan2Phy/RR_MoniLan2PhyPackType_Udp != 'On') and (/config_data/monitoring/MonitoringLan2Phy/RR_MoniLan2PhyPackType_Tcp != 'On'))";
                    type "lim_udp_port0";
                    must ". <= /config_data/monitoring/MonitoringLan2Phy/RR_MoniLan2PhyPortDstTo" {
                        error-message "valmsg_it_MoniLan2PhyPortDstFrom";
                    }
                }
                leaf "RR_MoniLan2PhyPortDstTo" {
                    when "not ((/config_data/monitoring/MonitoringLan2Phy/RR_MoniLan2PhyPackType_All != 'On') and (/config_data/monitoring/MonitoringLan2Phy/RR_MoniLan2PhyPackType_Udp != 'On') and (/config_data/monitoring/MonitoringLan2Phy/RR_MoniLan2PhyPackType_Tcp != 'On'))";
                    type "lim_udp_port0";
                    must ". >= /config_data/monitoring/MonitoringLan2Phy/RR_MoniLan2PhyPortDstFrom" {
                        error-message "valmsg_it_MoniLan2PhyPortDstTo";
                    }
                }
            }
            container "MonitoringLan3" {
                when "not (/config_data/device/DeviceHw/RR_DynHw_Port_Eth_Cnt <= 2)";
                leaf "RR_MoniLan3PhyIfEnabled" {
                    type "lbox_off_on";
                }
                leaf "RR_MoniLan3PhyRxEn" {
                    when "not (/config_data/monitoring/MonitoringLan3/RR_MoniLan3PhyIfEnabled != 'On')";
                    type "lbox_off_on";
                }
                leaf "RR_MoniLan3PhyTxEn" {
                    when "not (/config_data/monitoring/MonitoringLan3/RR_MoniLan3PhyIfEnabled != 'On')";
                    type "lbox_off_on";
                }
                leaf "RR_MoniLan3MonBandwidth" {
                    when "not (/config_data/monitoring/MonitoringLan3/RR_MoniLan3PhyIfEnabled != 'On')";
                    type "lbox_moni_max_bandwidth";
                }
            }
            container "MonitoringLan3Phy" {
                when "not ((/config_data/device/DeviceHw/RR_DynHw_Port_Eth_Cnt <= 2) or (/config_data/monitoring/MonitoringLan3/RR_MoniLan3PhyIfEnabled != 'On') or ((/config_data/monitoring/MonitoringLan3/RR_MoniLan3PhyRxEn != 'On') and (/config_data/monitoring/MonitoringLan3/RR_MoniLan3PhyTxEn != 'On')))";
                leaf "RR_MoniLan3PhyDispFrom" {
                    when "not (/config_data/monitoring/MonitoringLan3Phy/RR_MoniLan3PhyDispHeads = 'On')";
                    type "lim_uint_16";
                }
                leaf "RR_MoniLan3PhyDispLen" {
                    type "lim_uint_16";
                }
                leaf "RR_MoniLan3PhyDispHeads" {
                    type "lbox_off_on";
                }
                leaf "RR_MoniLan3PhyShowMTraffic" {
                    type "lbox_off_on";
                }
                leaf "RR_MoniLan3PhyPackType_All" {
                    type "lbox_off_on";
                }
                leaf "RR_MoniLan3PhyPackType_Udp" {
                    when "not (/config_data/monitoring/MonitoringLan3Phy/RR_MoniLan3PhyPackType_All = 'On')";
                    type "lbox_off_on";
                }
                leaf "RR_MoniLan3PhyPackType_Tcp" {
                    when "not (/config_data/monitoring/MonitoringLan3Phy/RR_MoniLan3PhyPackType_All = 'On')";
                    type "lbox_off_on";
                }
                leaf "RR_MoniLan3PhyPackType_Icmp" {
                    when "not (/config_data/monitoring/MonitoringLan3Phy/RR_MoniLan3PhyPackType_All = 'On')";
                    type "lbox_off_on";
                }
                leaf "RR_MoniLan3PhyPackType_Other" {
                    when "not (/config_data/monitoring/MonitoringLan3Phy/RR_MoniLan3PhyPackType_All = 'On')";
                    type "lbox_off_on";
                }
                leaf "RR_MoniLan3PhyPackType_Arp" {
                    when "not (/config_data/monitoring/MonitoringLan3Phy/RR_MoniLan3PhyPackType_All = 'On')";
                    type "lbox_off_on";
                }
                leaf "RR_MoniLan3PhyIpSrcMask" {
                    type "lim_ipv4_mask0";
                }
                leaf "RR_MoniLan3PhyIpSrc" {
                    type "inet:ipv4-address";
                }
                leaf "RR_MoniLan3PhyIpDst" {
                    type "inet:ipv4-address";
                }
                leaf "RR_MoniLan3PhyIpDstMask" {
                    type "lim_ipv4_mask0";
                }
                leaf "RR_MoniLan3PhyReverse" {
                    type "lbox_off_on";
                }
                leaf "RR_MoniLan3PhyPortSrcFrom" {
                    when "not ((/config_data/monitoring/MonitoringLan3Phy/RR_MoniLan3PhyPackType_All != 'On') and (/config_data/monitoring/MonitoringLan3Phy/RR_MoniLan3PhyPackType_Udp != 'On') and (/config_data/monitoring/MonitoringLan3Phy/RR_MoniLan3PhyPackType_Tcp != 'On'))";
                    type "lim_udp_port0";
                    must ". <= /config_data/monitoring/MonitoringLan3Phy/RR_MoniLan3PhyPortSrcTo" {
                        error-message "valmsg_it_MoniLan3PhyPortSrcFrom";
                    }
                }
                leaf "RR_MoniLan3PhyPortSrcTo" {
                    when "not ((/config_data/monitoring/MonitoringLan3Phy/RR_MoniLan3PhyPackType_All != 'On') and (/config_data/monitoring/MonitoringLan3Phy/RR_MoniLan3PhyPackType_Udp != 'On') and (/config_data/monitoring/MonitoringLan3Phy/RR_MoniLan3PhyPackType_Tcp != 'On'))";
                    type "lim_udp_port0";
                    must ". >= /config_data/monitoring/MonitoringLan3Phy/RR_MoniLan3PhyPortSrcFrom" {
                        error-message "valmsg_it_MoniLan3PhyPortSrcTo";
                    }
                }
                leaf "RR_MoniLan3PhyPortDstFrom" {
                    when "not ((/config_data/monitoring/MonitoringLan3Phy/RR_MoniLan3PhyPackType_All != 'On') and (/config_data/monitoring/MonitoringLan3Phy/RR_MoniLan3PhyPackType_Udp != 'On') and (/config_data/monitoring/MonitoringLan3Phy/RR_MoniLan3PhyPackType_Tcp != 'On'))";
                    type "lim_udp_port0";
                    must ". <= /config_data/monitoring/MonitoringLan3Phy/RR_MoniLan3PhyPortDstTo" {
                        error-message "valmsg_it_MoniLan3PhyPortDstFrom";
                    }
                }
                leaf "RR_MoniLan3PhyPortDstTo" {
                    when "not ((/config_data/monitoring/MonitoringLan3Phy/RR_MoniLan3PhyPackType_All != 'On') and (/config_data/monitoring/MonitoringLan3Phy/RR_MoniLan3PhyPackType_Udp != 'On') and (/config_data/monitoring/MonitoringLan3Phy/RR_MoniLan3PhyPackType_Tcp != 'On'))";
                    type "lim_udp_port0";
                    must ". >= /config_data/monitoring/MonitoringLan3Phy/RR_MoniLan3PhyPortDstFrom" {
                        error-message "valmsg_it_MoniLan3PhyPortDstTo";
                    }
                }
            }
            container "MonitoringLan4" {
                when "not (/config_data/device/DeviceHw/RR_DynHw_Port_Eth_Cnt <= 3)";
                leaf "RR_MoniLan4PhyIfEnabled" {
                    type "lbox_off_on";
                }
                leaf "RR_MoniLan4PhyRxEn" {
                    when "not (/config_data/monitoring/MonitoringLan4/RR_MoniLan4PhyIfEnabled != 'On')";
                    type "lbox_off_on";
                }
                leaf "RR_MoniLan4PhyTxEn" {
                    when "not (/config_data/monitoring/MonitoringLan4/RR_MoniLan4PhyIfEnabled != 'On')";
                    type "lbox_off_on";
                }
                leaf "RR_MoniLan4MonBandwidth" {
                    when "not (/config_data/monitoring/MonitoringLan4/RR_MoniLan4PhyIfEnabled != 'On')";
                    type "lbox_moni_max_bandwidth";
                }
            }
            container "MonitoringLan4Phy" {
                when "not ((/config_data/device/DeviceHw/RR_DynHw_Port_Eth_Cnt <= 3) or (/config_data/monitoring/MonitoringLan4/RR_MoniLan4PhyIfEnabled != 'On') or ((/config_data/monitoring/MonitoringLan4/RR_MoniLan4PhyRxEn != 'On') and (/config_data/monitoring/MonitoringLan4/RR_MoniLan4PhyTxEn != 'On')))";
                leaf "RR_MoniLan4PhyDispFrom" {
                    when "not (/config_data/monitoring/MonitoringLan4Phy/RR_MoniLan4PhyDispHeads = 'On')";
                    type "lim_uint_16";
                }
                leaf "RR_MoniLan4PhyDispLen" {
                    type "lim_uint_16";
                }
                leaf "RR_MoniLan4PhyDispHeads" {
                    type "lbox_off_on";
                }
                leaf "RR_MoniLan4PhyShowMTraffic" {
                    type "lbox_off_on";
                }
                leaf "RR_MoniLan4PhyPackType_All" {
                    type "lbox_off_on";
                }
                leaf "RR_MoniLan4PhyPackType_Udp" {
                    when "not (/config_data/monitoring/MonitoringLan4Phy/RR_MoniLan4PhyPackType_All = 'On')";
                    type "lbox_off_on";
                }
                leaf "RR_MoniLan4PhyPackType_Tcp" {
                    when "not (/config_data/monitoring/MonitoringLan4Phy/RR_MoniLan4PhyPackType_All = 'On')";
                    type "lbox_off_on";
                }
                leaf "RR_MoniLan4PhyPackType_Icmp" {
                    when "not (/config_data/monitoring/MonitoringLan4Phy/RR_MoniLan4PhyPackType_All = 'On')";
                    type "lbox_off_on";
                }
                leaf "RR_MoniLan4PhyPackType_Other" {
                    when "not (/config_data/monitoring/MonitoringLan4Phy/RR_MoniLan4PhyPackType_All = 'On')";
                    type "lbox_off_on";
                }
                leaf "RR_MoniLan4PhyPackType_Arp" {
                    when "not (/config_data/monitoring/MonitoringLan4Phy/RR_MoniLan4PhyPackType_All = 'On')";
                    type "lbox_off_on";
                }
                leaf "RR_MoniLan4PhyIpSrcMask" {
                    type "lim_ipv4_mask0";
                }
                leaf "RR_MoniLan4PhyIpSrc" {
                    type "inet:ipv4-address";
                }
                leaf "RR_MoniLan4PhyIpDst" {
                    type "inet:ipv4-address";
                }
                leaf "RR_MoniLan4PhyIpDstMask" {
                    type "lim_ipv4_mask0";
                }
                leaf "RR_MoniLan4PhyReverse" {
                    type "lbox_off_on";
                }
                leaf "RR_MoniLan4PhyPortSrcFrom" {
                    when "not ((/config_data/monitoring/MonitoringLan4Phy/RR_MoniLan4PhyPackType_All != 'On') and (/config_data/monitoring/MonitoringLan4Phy/RR_MoniLan4PhyPackType_Udp != 'On') and (/config_data/monitoring/MonitoringLan4Phy/RR_MoniLan4PhyPackType_Tcp != 'On'))";
                    type "lim_udp_port0";
                    must ". <= /config_data/monitoring/MonitoringLan4Phy/RR_MoniLan4PhyPortSrcTo" {
                        error-message "valmsg_it_MoniLan4PhyPortSrcFrom";
                    }
                }
                leaf "RR_MoniLan4PhyPortSrcTo" {
                    when "not ((/config_data/monitoring/MonitoringLan4Phy/RR_MoniLan4PhyPackType_All != 'On') and (/config_data/monitoring/MonitoringLan4Phy/RR_MoniLan4PhyPackType_Udp != 'On') and (/config_data/monitoring/MonitoringLan4Phy/RR_MoniLan4PhyPackType_Tcp != 'On'))";
                    type "lim_udp_port0";
                    must ". >= /config_data/monitoring/MonitoringLan4Phy/RR_MoniLan4PhyPortSrcFrom" {
                        error-message "valmsg_it_MoniLan4PhyPortSrcTo";
                    }
                }
                leaf "RR_MoniLan4PhyPortDstFrom" {
                    when "not ((/config_data/monitoring/MonitoringLan4Phy/RR_MoniLan4PhyPackType_All != 'On') and (/config_data/monitoring/MonitoringLan4Phy/RR_MoniLan4PhyPackType_Udp != 'On') and (/config_data/monitoring/MonitoringLan4Phy/RR_MoniLan4PhyPackType_Tcp != 'On'))";
                    type "lim_udp_port0";
                    must ". <= /config_data/monitoring/MonitoringLan4Phy/RR_MoniLan4PhyPortDstTo" {
                        error-message "valmsg_it_MoniLan4PhyPortDstFrom";
                    }
                }
                leaf "RR_MoniLan4PhyPortDstTo" {
                    when "not ((/config_data/monitoring/MonitoringLan4Phy/RR_MoniLan4PhyPackType_All != 'On') and (/config_data/monitoring/MonitoringLan4Phy/RR_MoniLan4PhyPackType_Udp != 'On') and (/config_data/monitoring/MonitoringLan4Phy/RR_MoniLan4PhyPackType_Tcp != 'On'))";
                    type "lim_udp_port0";
                    must ". >= /config_data/monitoring/MonitoringLan4Phy/RR_MoniLan4PhyPortDstFrom" {
                        error-message "valmsg_it_MoniLan4PhyPortDstTo";
                    }
                }
            }
            container "MonitoringLan5" {
                when "not (/config_data/device/DeviceHw/RR_DynHw_Port_Sfp != 'On')";
                leaf "RR_MoniLan5PhyIfEnabled" {
                    type "lbox_off_on";
                }
                leaf "RR_MoniLan5PhyRxEn" {
                    when "not (/config_data/monitoring/MonitoringLan5/RR_MoniLan5PhyIfEnabled != 'On')";
                    type "lbox_off_on";
                }
                leaf "RR_MoniLan5PhyTxEn" {
                    when "not (/config_data/monitoring/MonitoringLan5/RR_MoniLan5PhyIfEnabled != 'On')";
                    type "lbox_off_on";
                }
                leaf "RR_MoniLan5MonBandwidth" {
                    when "not (/config_data/monitoring/MonitoringLan5/RR_MoniLan5PhyIfEnabled != 'On')";
                    type "lbox_moni_max_bandwidth";
                }
            }
            container "MonitoringLan5Phy" {
                when "not ((/config_data/device/DeviceHw/RR_DynHw_Port_Sfp != 'On') or (/config_data/monitoring/MonitoringLan5/RR_MoniLan5PhyIfEnabled != 'On') or ((/config_data/monitoring/MonitoringLan5/RR_MoniLan5PhyRxEn != 'On') and (/config_data/monitoring/MonitoringLan5/RR_MoniLan5PhyTxEn != 'On')))";
                leaf "RR_MoniLan5PhyDispFrom" {
                    when "not (/config_data/monitoring/MonitoringLan5Phy/RR_MoniLan5PhyDispHeads = 'On')";
                    type "lim_uint_16";
                }
                leaf "RR_MoniLan5PhyDispLen" {
                    type "lim_uint_16";
                }
                leaf "RR_MoniLan5PhyDispHeads" {
                    type "lbox_off_on";
                }
                leaf "RR_MoniLan5PhyShowMTraffic" {
                    type "lbox_off_on";
                }
                leaf "RR_MoniLan5PhyPackType_All" {
                    type "lbox_off_on";
                }
                leaf "RR_MoniLan5PhyPackType_Udp" {
                    when "not (/config_data/monitoring/MonitoringLan5Phy/RR_MoniLan5PhyPackType_All = 'On')";
                    type "lbox_off_on";
                }
                leaf "RR_MoniLan5PhyPackType_Tcp" {
                    when "not (/config_data/monitoring/MonitoringLan5Phy/RR_MoniLan5PhyPackType_All = 'On')";
                    type "lbox_off_on";
                }
                leaf "RR_MoniLan5PhyPackType_Icmp" {
                    when "not (/config_data/monitoring/MonitoringLan5Phy/RR_MoniLan5PhyPackType_All = 'On')";
                    type "lbox_off_on";
                }
                leaf "RR_MoniLan5PhyPackType_Other" {
                    when "not (/config_data/monitoring/MonitoringLan5Phy/RR_MoniLan5PhyPackType_All = 'On')";
                    type "lbox_off_on";
                }
                leaf "RR_MoniLan5PhyPackType_Arp" {
                    when "not (/config_data/monitoring/MonitoringLan5Phy/RR_MoniLan5PhyPackType_All = 'On')";
                    type "lbox_off_on";
                }
                leaf "RR_MoniLan5PhyIpSrcMask" {
                    type "lim_ipv4_mask0";
                }
                leaf "RR_MoniLan5PhyIpSrc" {
                    type "inet:ipv4-address";
                }
                leaf "RR_MoniLan5PhyIpDst" {
                    type "inet:ipv4-address";
                }
                leaf "RR_MoniLan5PhyIpDstMask" {
                    type "lim_ipv4_mask0";
                }
                leaf "RR_MoniLan5PhyReverse" {
                    type "lbox_off_on";
                }
                leaf "RR_MoniLan5PhyPortSrcFrom" {
                    when "not ((/config_data/monitoring/MonitoringLan5Phy/RR_MoniLan5PhyPackType_All != 'On') and (/config_data/monitoring/MonitoringLan5Phy/RR_MoniLan5PhyPackType_Udp != 'On') and (/config_data/monitoring/MonitoringLan5Phy/RR_MoniLan5PhyPackType_Tcp != 'On'))";
                    type "lim_udp_port0";
                    must ". <= /config_data/monitoring/MonitoringLan5Phy/RR_MoniLan5PhyPortSrcTo" {
                        error-message "valmsg_it_MoniLan5PhyPortSrcFrom";
                    }
                }
                leaf "RR_MoniLan5PhyPortSrcTo" {
                    when "not ((/config_data/monitoring/MonitoringLan5Phy/RR_MoniLan5PhyPackType_All != 'On') and (/config_data/monitoring/MonitoringLan5Phy/RR_MoniLan5PhyPackType_Udp != 'On') and (/config_data/monitoring/MonitoringLan5Phy/RR_MoniLan5PhyPackType_Tcp != 'On'))";
                    type "lim_udp_port0";
                    must ". >= /config_data/monitoring/MonitoringLan5Phy/RR_MoniLan5PhyPortSrcFrom" {
                        error-message "valmsg_it_MoniLan5PhyPortSrcTo";
                    }
                }
                leaf "RR_MoniLan5PhyPortDstFrom" {
                    when "not ((/config_data/monitoring/MonitoringLan5Phy/RR_MoniLan5PhyPackType_All != 'On') and (/config_data/monitoring/MonitoringLan5Phy/RR_MoniLan5PhyPackType_Udp != 'On') and (/config_data/monitoring/MonitoringLan5Phy/RR_MoniLan5PhyPackType_Tcp != 'On'))";
                    type "lim_udp_port0";
                    must ". <= /config_data/monitoring/MonitoringLan5Phy/RR_MoniLan5PhyPortDstTo" {
                        error-message "valmsg_it_MoniLan5PhyPortDstFrom";
                    }
                }
                leaf "RR_MoniLan5PhyPortDstTo" {
                    when "not ((/config_data/monitoring/MonitoringLan5Phy/RR_MoniLan5PhyPackType_All != 'On') and (/config_data/monitoring/MonitoringLan5Phy/RR_MoniLan5PhyPackType_Udp != 'On') and (/config_data/monitoring/MonitoringLan5Phy/RR_MoniLan5PhyPackType_Tcp != 'On'))";
                    type "lim_udp_port0";
                    must ". >= /config_data/monitoring/MonitoringLan5Phy/RR_MoniLan5PhyPortDstFrom" {
                        error-message "valmsg_it_MoniLan5PhyPortDstTo";
                    }
                }
            }
            container "MonitoringRfc" {
                when "not (/config_data/device/DeviceHw/RR_DynHw_Primary_Radio != 'On')";
                leaf "RR_MoniRfcIprIfEnabled" {
                    type "lbox_off_on";
                }
                leaf "RR_MoniRfcIprRxEn" {
                    when "not (/config_data/monitoring/MonitoringRfc/RR_MoniRfcIprIfEnabled != 'On')";
                    type "lbox_off_on";
                }
                leaf "RR_MoniRfcIprTxEn" {
                    when "not (/config_data/monitoring/MonitoringRfc/RR_MoniRfcIprIfEnabled != 'On')";
                    type "lbox_off_on";
                }
                leaf "RR_MoniRfcPhyIfEnabled" {
                    type "lbox_off_on";
                }
                leaf "RR_MoniRfcPhyRxEn" {
                    when "not (/config_data/monitoring/MonitoringRfc/RR_MoniRfcPhyIfEnabled != 'On')";
                    type "lbox_off_on";
                }
                leaf "RR_MoniRfcPhyTxEn" {
                    when "not (/config_data/monitoring/MonitoringRfc/RR_MoniRfcPhyIfEnabled != 'On')";
                    type "lbox_off_on";
                }
                leaf "RR_MoniRfcMonBandwidth" {
                    when "not ((/config_data/monitoring/MonitoringRfc/RR_MoniRfcPhyIfEnabled != 'On') and (/config_data/monitoring/MonitoringRfc/RR_MoniRfcIprIfEnabled != 'On'))";
                    type "lbox_moni_max_bandwidth";
                }
                leaf "RR_MoniRfcMeasIfEnabled" {
                    type "lbox_off_on";
                }
            }
            container "MonitoringRfcIpr" {
                when "not ((/config_data/device/DeviceHw/RR_DynHw_Primary_Radio != 'On') or (/config_data/monitoring/MonitoringRfc/RR_MoniRfcIprIfEnabled != 'On') or ((/config_data/monitoring/MonitoringRfc/RR_MoniRfcIprRxEn != 'On') and (/config_data/monitoring/MonitoringRfc/RR_MoniRfcIprTxEn != 'On')))";
                leaf "RR_MoniRfcIprPackType_All" {
                    type "lbox_off_on";
                }
                leaf "RR_MoniRfcIprPackType_Udp" {
                    when "not (/config_data/monitoring/MonitoringRfcIpr/RR_MoniRfcIprPackType_All = 'On')";
                    type "lbox_off_on";
                }
                leaf "RR_MoniRfcIprPackType_Tcp" {
                    when "not (/config_data/monitoring/MonitoringRfcIpr/RR_MoniRfcIprPackType_All = 'On')";
                    type "lbox_off_on";
                }
                leaf "RR_MoniRfcIprPackType_Icmp" {
                    when "not (/config_data/monitoring/MonitoringRfcIpr/RR_MoniRfcIprPackType_All = 'On')";
                    type "lbox_off_on";
                }
                leaf "RR_MoniRfcIprPackType_Other" {
                    when "not (/config_data/monitoring/MonitoringRfcIpr/RR_MoniRfcIprPackType_All = 'On')";
                    type "lbox_off_on";
                }
                leaf "RR_MoniRfcIprPackType_Arp" {
                    when "not (/config_data/monitoring/MonitoringRfcIpr/RR_MoniRfcIprPackType_All = 'On')";
                    type "lbox_off_on";
                }
                leaf "RR_MoniRfcIprDispHeads" {
                    type "enumeration" {
                        enum "None" {
                            value "0";
                        }
                        enum "Packet (IP)" {
                            value "1";
                        }
                        enum "Frame (ETH)" {
                            value "2";
                        }
                    }
                }
                leaf "RR_MoniRfcIprDispFrom" {
                    type "lim_uint_16";
                }
                leaf "RR_MoniRfcIprDispLen" {
                    type "lim_uint_16";
                }
                leaf "RR_MoniRfcIprIpSrc" {
                    type "inet:ipv4-address";
                }
                leaf "RR_MoniRfcIprIpDst" {
                    type "inet:ipv4-address";
                }
                leaf "RR_MoniRfcIprIpSrcMask" {
                    type "lim_ipv4_mask0";
                }
                leaf "RR_MoniRfcIprIpDstMask" {
                    type "lim_ipv4_mask0";
                }
                leaf "RR_MoniRfcIprReverse" {
                    type "lbox_off_on";
                }
                leaf "RR_MoniRfcIprPortSrcFrom" {
                    when "not ((/config_data/monitoring/MonitoringRfcIpr/RR_MoniRfcIprPackType_All != 'On') and (/config_data/monitoring/MonitoringRfcIpr/RR_MoniRfcIprPackType_Udp != 'On') and (/config_data/monitoring/MonitoringRfcIpr/RR_MoniRfcIprPackType_Tcp != 'On'))";
                    type "lim_udp_port0";
                    must ". <= /config_data/monitoring/MonitoringRfcIpr/RR_MoniRfcIprPortSrcTo" {
                        error-message "valmsg_it_MoniRfcIprPortSrcFrom";
                    }
                }
                leaf "RR_MoniRfcIprPortSrcTo" {
                    when "not ((/config_data/monitoring/MonitoringRfcIpr/RR_MoniRfcIprPackType_All != 'On') and (/config_data/monitoring/MonitoringRfcIpr/RR_MoniRfcIprPackType_Udp != 'On') and (/config_data/monitoring/MonitoringRfcIpr/RR_MoniRfcIprPackType_Tcp != 'On'))";
                    type "lim_udp_port0";
                    must ". >= /config_data/monitoring/MonitoringRfcIpr/RR_MoniRfcIprPortSrcFrom" {
                        error-message "valmsg_it_MoniRfcIprPortSrcTo";
                    }
                }
                leaf "RR_MoniRfcIprPortDstFrom" {
                    when "not ((/config_data/monitoring/MonitoringRfcIpr/RR_MoniRfcIprPackType_All != 'On') and (/config_data/monitoring/MonitoringRfcIpr/RR_MoniRfcIprPackType_Udp != 'On') and (/config_data/monitoring/MonitoringRfcIpr/RR_MoniRfcIprPackType_Tcp != 'On'))";
                    type "lim_udp_port0";
                    must ". <= /config_data/monitoring/MonitoringRfcIpr/RR_MoniRfcIprPortDstTo" {
                        error-message "valmsg_it_MoniRfcIprPortDstFrom";
                    }
                }
                leaf "RR_MoniRfcIprPortDstTo" {
                    when "not ((/config_data/monitoring/MonitoringRfcIpr/RR_MoniRfcIprPackType_All != 'On') and (/config_data/monitoring/MonitoringRfcIpr/RR_MoniRfcIprPackType_Udp != 'On') and (/config_data/monitoring/MonitoringRfcIpr/RR_MoniRfcIprPackType_Tcp != 'On'))";
                    type "lim_udp_port0";
                    must ". >= /config_data/monitoring/MonitoringRfcIpr/RR_MoniRfcIprPortDstFrom" {
                        error-message "valmsg_it_MoniRfcIprPortDstTo";
                    }
                }
            }
            container "MonitoringRfcPhy" {
                when "not ((/config_data/device/DeviceHw/RR_DynHw_Primary_Radio != 'On') or (/config_data/monitoring/MonitoringRfc/RR_MoniRfcPhyIfEnabled != 'On') or ((/config_data/monitoring/MonitoringRfc/RR_MoniRfcPhyRxEn != 'On') and (/config_data/monitoring/MonitoringRfc/RR_MoniRfcPhyTxEn != 'On')))";
                leaf "RR_MoniRfcPhyPackType_All" {
                    type "lbox_off_on";
                }
                leaf "RR_MoniRfcPhyPackType_Udp" {
                    when "not (/config_data/monitoring/MonitoringRfcPhy/RR_MoniRfcPhyPackType_All = 'On')";
                    type "lbox_off_on";
                }
                leaf "RR_MoniRfcPhyPackType_Tcp" {
                    when "not (/config_data/monitoring/MonitoringRfcPhy/RR_MoniRfcPhyPackType_All = 'On')";
                    type "lbox_off_on";
                }
                leaf "RR_MoniRfcPhyPackType_Icmp" {
                    when "not (/config_data/monitoring/MonitoringRfcPhy/RR_MoniRfcPhyPackType_All = 'On')";
                    type "lbox_off_on";
                }
                leaf "RR_MoniRfcPhyPackType_Other" {
                    when "not (/config_data/monitoring/MonitoringRfcPhy/RR_MoniRfcPhyPackType_All = 'On')";
                    type "lbox_off_on";
                }
                leaf "RR_MoniRfcPhyPackType_Arp" {
                    when "not (/config_data/monitoring/MonitoringRfcPhy/RR_MoniRfcPhyPackType_All = 'On')";
                    type "lbox_off_on";
                }
                leaf "RR_MoniRfcPhyShowCorrupted" {
                    type "lbox_off_on";
                }
                leaf "RR_MoniRfcPhyShowOtherModeFr" {
                    type "lbox_off_on";
                }
                leaf "RR_MoniRfcPhyDispHeads" {
                    type "enumeration" {
                        enum "None" {
                            value "0";
                        }
                        enum "Radio Link" {
                            value "1";
                        }
                        enum "Data Coding" {
                            value "2";
                        }
                        enum "Both" {
                            value "3";
                        }
                    }
                }
                leaf "RR_MoniRfcPhyPromiscMode" {
                    type "lbox_off_on";
                }
                leaf "RR_MoniRfcPhyShowLcf" {
                    type "lbox_off_on";
                }
                leaf "RR_MoniRfcPhyDispFrom" {
                    type "lim_uint_16";
                }
                leaf "RR_MoniRfcPhyDispLen" {
                    type "lim_uint_16";
                }
                leaf "RR_MoniRfcPhyIpSrc" {
                    type "inet:ipv4-address";
                }
                leaf "RR_MoniRfcPhyIpDst" {
                    type "inet:ipv4-address";
                }
                leaf "RR_MoniRfcPhyIpSrcMask" {
                    type "lim_ipv4_mask0";
                }
                leaf "RR_MoniRfcPhyIpDstMask" {
                    type "lim_ipv4_mask0";
                }
                leaf "RR_MoniRfcPhyReverse" {
                    type "lbox_off_on";
                }
                leaf "RR_MoniRfcPhyIpRadioSrc" {
                    type "inet:ipv4-address";
                }
                leaf "RR_MoniRfcPhyIpRadioDst" {
                    type "inet:ipv4-address";
                }
                leaf "RR_MoniRfcPhyIpRadioSrcMask" {
                    type "lim_ipv4_mask0";
                }
                leaf "RR_MoniRfcPhyIpRadioDstMask" {
                    type "lim_ipv4_mask0";
                }
                leaf "RR_MoniRfcPhyRadioReverse" {
                    type "lbox_off_on";
                }
                leaf "RR_MoniRfcPhyExtendedMeas" {
                    type "lbox_off_on";
                }
                leaf "RR_MoniRfcPhyPortSrcFrom" {
                    when "not ((/config_data/monitoring/MonitoringRfcPhy/RR_MoniRfcPhyPackType_All != 'On') and (/config_data/monitoring/MonitoringRfcPhy/RR_MoniRfcPhyPackType_Udp != 'On') and (/config_data/monitoring/MonitoringRfcPhy/RR_MoniRfcPhyPackType_Tcp != 'On'))";
                    type "lim_udp_port0";
                    must ". <= /config_data/monitoring/MonitoringRfcPhy/RR_MoniRfcPhyPortSrcTo" {
                        error-message "valmsg_it_MoniRfcPhyPortSrcFrom";
                    }
                }
                leaf "RR_MoniRfcPhyPortSrcTo" {
                    when "not ((/config_data/monitoring/MonitoringRfcPhy/RR_MoniRfcPhyPackType_All != 'On') and (/config_data/monitoring/MonitoringRfcPhy/RR_MoniRfcPhyPackType_Udp != 'On') and (/config_data/monitoring/MonitoringRfcPhy/RR_MoniRfcPhyPackType_Tcp != 'On'))";
                    type "lim_udp_port0";
                    must ". >= /config_data/monitoring/MonitoringRfcPhy/RR_MoniRfcPhyPortSrcFrom" {
                        error-message "valmsg_it_MoniRfcPhyPortSrcTo";
                    }
                }
                leaf "RR_MoniRfcPhyPortDstFrom" {
                    when "not ((/config_data/monitoring/MonitoringRfcPhy/RR_MoniRfcPhyPackType_All != 'On') and (/config_data/monitoring/MonitoringRfcPhy/RR_MoniRfcPhyPackType_Udp != 'On') and (/config_data/monitoring/MonitoringRfcPhy/RR_MoniRfcPhyPackType_Tcp != 'On'))";
                    type "lim_udp_port0";
                    must ". <= /config_data/monitoring/MonitoringRfcPhy/RR_MoniRfcPhyPortDstTo" {
                        error-message "valmsg_it_MoniRfcPhyPortDstFrom";
                    }
                }
                leaf "RR_MoniRfcPhyPortDstTo" {
                    when "not ((/config_data/monitoring/MonitoringRfcPhy/RR_MoniRfcPhyPackType_All != 'On') and (/config_data/monitoring/MonitoringRfcPhy/RR_MoniRfcPhyPackType_Udp != 'On') and (/config_data/monitoring/MonitoringRfcPhy/RR_MoniRfcPhyPackType_Tcp != 'On'))";
                    type "lim_udp_port0";
                    must ". >= /config_data/monitoring/MonitoringRfcPhy/RR_MoniRfcPhyPortDstFrom" {
                        error-message "valmsg_it_MoniRfcPhyPortDstTo";
                    }
                }
            }
            container "MonitoringRfcMeas" {
                when "not ((/config_data/device/DeviceHw/RR_DynHw_Primary_Radio != 'On') or (/config_data/monitoring/MonitoringRfc/RR_MoniRfcMeasIfEnabled != 'On'))";
                leaf "RR_MoniRfcMeasRssEn" {
                    type "lbox_off_on";
                }
                leaf "RR_MoniRfcMeasRssPeriod" {
                    when "not (/config_data/monitoring/MonitoringRfcMeas/RR_MoniRfcMeasRssEn != 'On')";
                    type "uint16" {
                        range "50..5000";
                    }
                }
                leaf "RR_MoniRfcMeasBbpEn" {
                    when "not (/config_data/device/DeviceHw/RR_DynHw_Radio_BBP_measurement != 'On')";
                    type "lbox_off_on";
                }
            }
            container "MonitoringWWANAux" {
                when "not ((/config_data/device/DeviceHw/RR_DynHw_Module_Cellular != 'On') and (/config_data/device/DeviceHw/RR_DynHw_Module_Wifi != 'On'))";
                leaf "RR_MoniWWANAuxPhyIfEnabled" {
                    type "lbox_off_on";
                }
                leaf "RR_MoniWWANAuxPhyRxEn" {
                    when "not (/config_data/monitoring/MonitoringWWANAux/RR_MoniWWANAuxPhyIfEnabled != 'On')";
                    type "lbox_off_on";
                }
                leaf "RR_MoniWWANAuxPhyTxEn" {
                    when "not (/config_data/monitoring/MonitoringWWANAux/RR_MoniWWANAuxPhyIfEnabled != 'On')";
                    type "lbox_off_on";
                }
                leaf "RR_MoniWWANAuxMonBandwidth" {
                    when "not (/config_data/monitoring/MonitoringWWANAux/RR_MoniWWANAuxPhyIfEnabled != 'On')";
                    type "lbox_moni_max_bandwidth";
                    description "Monitoring - WWANAux - limit: monitoring bandwidth";
                }
            }
            container "MonitoringWWANAuxPhy" {
                when "not ((/config_data/monitoring/MonitoringWWANAux/RR_MoniWWANAuxPhyIfEnabled != 'On') or ((/config_data/device/DeviceHw/RR_DynHw_Module_Cellular != 'On') and (/config_data/device/DeviceHw/RR_DynHw_Module_Wifi != 'On')) or ((/config_data/monitoring/MonitoringWWANAux/RR_MoniWWANAuxPhyRxEn != 'On') and (/config_data/monitoring/MonitoringWWANAux/RR_MoniWWANAuxPhyTxEn != 'On')))";
                leaf "RR_MoniWWANAuxPhyDispFrom" {
                    when "not (/config_data/monitoring/MonitoringWWANAuxPhy/RR_MoniWWANAuxPhyDispHeads = 'On')";
                    type "lim_uint_16";
                }
                leaf "RR_MoniWWANAuxPhyDispLen" {
                    type "lim_uint_16";
                }
                leaf "RR_MoniWWANAuxPhyDispHeads" {
                    type "lbox_off_on";
                }
                leaf "RR_MoniWWANAuxPhyShowMTraffic" {
                    type "lbox_off_on";
                }
                leaf "RR_MoniWWANAuxPhyPackType_All" {
                    type "lbox_off_on";
                    description "Monitoring - WWANAux - filter: packet type - all";
                }
                leaf "RR_MoniWWANAuxPhyPackType_Udp" {
                    when "not (/config_data/monitoring/MonitoringWWANAuxPhy/RR_MoniWWANAuxPhyPackType_All = 'On')";
                    type "lbox_off_on";
                    description "Monitoring - WWANAux - filter: packet type - UDP";
                }
                leaf "RR_MoniWWANAuxPhyPackType_Tcp" {
                    when "not (/config_data/monitoring/MonitoringWWANAuxPhy/RR_MoniWWANAuxPhyPackType_All = 'On')";
                    type "lbox_off_on";
                    description "Monitoring - WWANAux - filter: packet type - TCP";
                }
                leaf "RR_MoniWWANAuxPhyPackType_Icmp" {
                    when "not (/config_data/monitoring/MonitoringWWANAuxPhy/RR_MoniWWANAuxPhyPackType_All = 'On')";
                    type "lbox_off_on";
                    description "Monitoring - WWANAux - filter: packet type - ICMP";
                }
                leaf "RR_MoniWWANAuxPhyPackType_Other" {
                    when "not (/config_data/monitoring/MonitoringWWANAuxPhy/RR_MoniWWANAuxPhyPackType_All = 'On')";
                    type "lbox_off_on";
                    description "Monitoring - WWANAux - filter: packet type - other";
                }
                leaf "RR_MoniWWANAuxPhyPackType_Arp" {
                    when "not (/config_data/monitoring/MonitoringWWANAuxPhy/RR_MoniWWANAuxPhyPackType_All = 'On')";
                    type "lbox_off_on";
                    description "Monitoring - WWANAux - filter: packet type - ARP";
                }
                leaf "RR_MoniWWANAuxPhyIpSrc" {
                    type "inet:ipv4-address";
                    description "Monitoring - WWANAux - filter: IP source";
                }
                leaf "RR_MoniWWANAuxPhyIpDst" {
                    type "inet:ipv4-address";
                    description "Monitoring - WWANAux - filter: IP destination";
                }
                leaf "RR_MoniWWANAuxPhyIpSrcMask" {
                    type "lim_ipv4_mask0";
                    description "Monitoring - WWANAux - filter: IP source";
                }
                leaf "RR_MoniWWANAuxPhyIpDstMask" {
                    type "lim_ipv4_mask0";
                    description "Monitoring - WWANAux - filter: IP destination";
                }
                leaf "RR_MoniWWANAuxPhyReverse" {
                    type "lbox_off_on";
                    description "Monitoring - WWANAux - filter: include reverse direction";
                }
                leaf "RR_MoniWWANAuxPhyPortSrcFrom" {
                    when "not ((/config_data/monitoring/MonitoringWWANAuxPhy/RR_MoniWWANAuxPhyPackType_All != 'On') and (/config_data/monitoring/MonitoringWWANAuxPhy/RR_MoniWWANAuxPhyPackType_Udp != 'On') and (/config_data/monitoring/MonitoringWWANAuxPhy/RR_MoniWWANAuxPhyPackType_Tcp != 'On'))";
                    type "lim_udp_port0";
                    must ". <= /config_data/monitoring/MonitoringWWANAuxPhy/RR_MoniWWANAuxPhyPortSrcTo" {
                        error-message "valmsg_it_MoniWWANAuxPhyPortSrcFrom";
                    }
                    description "Monitoring - WWANAux - filter: source port (from)";
                }
                leaf "RR_MoniWWANAuxPhyPortSrcTo" {
                    when "not ((/config_data/monitoring/MonitoringWWANAuxPhy/RR_MoniWWANAuxPhyPackType_All != 'On') and (/config_data/monitoring/MonitoringWWANAuxPhy/RR_MoniWWANAuxPhyPackType_Udp != 'On') and (/config_data/monitoring/MonitoringWWANAuxPhy/RR_MoniWWANAuxPhyPackType_Tcp != 'On'))";
                    type "lim_udp_port0";
                    must ". >= /config_data/monitoring/MonitoringWWANAuxPhy/RR_MoniWWANAuxPhyPortSrcFrom" {
                        error-message "valmsg_it_MoniWWANAuxPhyPortSrcTo";
                    }
                    description "Monitoring - WWANAux - filter: source port (to)";
                }
                leaf "RR_MoniWWANAuxPhyPortDstFrom" {
                    when "not ((/config_data/monitoring/MonitoringWWANAuxPhy/RR_MoniWWANAuxPhyPackType_All != 'On') and (/config_data/monitoring/MonitoringWWANAuxPhy/RR_MoniWWANAuxPhyPackType_Udp != 'On') and (/config_data/monitoring/MonitoringWWANAuxPhy/RR_MoniWWANAuxPhyPackType_Tcp != 'On'))";
                    type "lim_udp_port0";
                    must ". <= /config_data/monitoring/MonitoringWWANAuxPhy/RR_MoniWWANAuxPhyPortDstTo" {
                        error-message "valmsg_it_MoniWWANAuxPhyPortDstFrom";
                    }
                    description "Monitoring - WWANAux - filter: destination port (from)";
                }
                leaf "RR_MoniWWANAuxPhyPortDstTo" {
                    when "not ((/config_data/monitoring/MonitoringWWANAuxPhy/RR_MoniWWANAuxPhyPackType_All != 'On') and (/config_data/monitoring/MonitoringWWANAuxPhy/RR_MoniWWANAuxPhyPackType_Udp != 'On') and (/config_data/monitoring/MonitoringWWANAuxPhy/RR_MoniWWANAuxPhyPackType_Tcp != 'On'))";
                    type "lim_udp_port0";
                    must ". >= /config_data/monitoring/MonitoringWWANAuxPhy/RR_MoniWWANAuxPhyPortDstFrom" {
                        error-message "valmsg_it_MoniWWANAuxPhyPortDstTo";
                    }
                    description "Monitoring - WWANAux - filter: destination port (to)";
                }
            }
            container "MonitoringWWANMain" {
                when "not (/config_data/device/DeviceHw/RR_DynHw_Primary_Cellular != 'On')";
                leaf "RR_MoniWWANMainPhyIfEnabled" {
                    type "lbox_off_on";
                }
                leaf "RR_MoniWWANMainPhyRxEn" {
                    when "not (/config_data/monitoring/MonitoringWWANMain/RR_MoniWWANMainPhyIfEnabled != 'On')";
                    type "lbox_off_on";
                }
                leaf "RR_MoniWWANMainPhyTxEn" {
                    when "not (/config_data/monitoring/MonitoringWWANMain/RR_MoniWWANMainPhyIfEnabled != 'On')";
                    type "lbox_off_on";
                }
                leaf "RR_MoniWWANMainMonBandwidth" {
                    when "not (/config_data/monitoring/MonitoringWWANMain/RR_MoniWWANMainPhyIfEnabled != 'On')";
                    type "lbox_moni_max_bandwidth";
                    description "Monitoring - WWANMain - limit: monitoring bandwidth";
                }
            }
            container "MonitoringWWANMainPhy" {
                when "not ((/config_data/monitoring/MonitoringWWANMain/RR_MoniWWANMainPhyIfEnabled != 'On') or (/config_data/device/DeviceHw/RR_DynHw_Primary_Cellular != 'On') or ((/config_data/monitoring/MonitoringWWANMain/RR_MoniWWANMainPhyRxEn != 'On') and (/config_data/monitoring/MonitoringWWANMain/RR_MoniWWANMainPhyTxEn != 'On')))";
                leaf "RR_MoniWWANMainPhyDispFrom" {
                    when "not (/config_data/monitoring/MonitoringWWANMainPhy/RR_MoniWWANMainPhyDispHeads = 'On')";
                    type "lim_uint_16";
                }
                leaf "RR_MoniWWANMainPhyDispLen" {
                    type "lim_uint_16";
                }
                leaf "RR_MoniWWANMainPhyDispHeads" {
                    type "lbox_off_on";
                }
                leaf "RR_MoniWWANMainPhyShowMTraffic" {
                    type "lbox_off_on";
                }
                leaf "RR_MoniWWANMainPhyPackType_All" {
                    type "lbox_off_on";
                    description "Monitoring - WWANMain - filter: packet type - all";
                }
                leaf "RR_MoniWWANMainPhyPackType_Udp" {
                    when "not (/config_data/monitoring/MonitoringWWANMainPhy/RR_MoniWWANMainPhyPackType_All = 'On')";
                    type "lbox_off_on";
                    description "Monitoring - WWANMain - filter: packet type - UDP";
                }
                leaf "RR_MoniWWANMainPhyPackType_Tcp" {
                    when "not (/config_data/monitoring/MonitoringWWANMainPhy/RR_MoniWWANMainPhyPackType_All = 'On')";
                    type "lbox_off_on";
                    description "Monitoring - WWANMain - filter: packet type - TCP";
                }
                leaf "RR_MoniWWANMainPhyPackType_Icmp" {
                    when "not (/config_data/monitoring/MonitoringWWANMainPhy/RR_MoniWWANMainPhyPackType_All = 'On')";
                    type "lbox_off_on";
                    description "Monitoring - WWANMain - filter: packet type - ICMP";
                }
                leaf "RR_MoniWWANMainPhyPackType_Other" {
                    when "not (/config_data/monitoring/MonitoringWWANMainPhy/RR_MoniWWANMainPhyPackType_All = 'On')";
                    type "lbox_off_on";
                    description "Monitoring - WWANMain - filter: packet type - other";
                }
                leaf "RR_MoniWWANMainPhyPackType_Arp" {
                    when "not (/config_data/monitoring/MonitoringWWANMainPhy/RR_MoniWWANMainPhyPackType_All = 'On')";
                    type "lbox_off_on";
                    description "Monitoring - WWANMain - filter: packet type - ARP";
                }
                leaf "RR_MoniWWANMainPhyIpSrc" {
                    type "inet:ipv4-address";
                    description "Monitoring - WWANMain - filter: IP source";
                }
                leaf "RR_MoniWWANMainPhyIpDst" {
                    type "inet:ipv4-address";
                    description "Monitoring - WWANMain - filter: IP destination";
                }
                leaf "RR_MoniWWANMainPhyIpSrcMask" {
                    type "lim_ipv4_mask0";
                    description "Monitoring - WWANMain - filter: IP source";
                }
                leaf "RR_MoniWWANMainPhyIpDstMask" {
                    type "lim_ipv4_mask0";
                    description "Monitoring - WWANMain - filter: IP destination";
                }
                leaf "RR_MoniWWANMainPhyReverse" {
                    type "lbox_off_on";
                    description "Monitoring - WWANMain - filter: include reverse direction";
                }
                leaf "RR_MoniWWANMainPhyPortSrcFrom" {
                    when "not ((/config_data/monitoring/MonitoringWWANMainPhy/RR_MoniWWANMainPhyPackType_All != 'On') and (/config_data/monitoring/MonitoringWWANMainPhy/RR_MoniWWANMainPhyPackType_Udp != 'On') and (/config_data/monitoring/MonitoringWWANMainPhy/RR_MoniWWANMainPhyPackType_Tcp != 'On'))";
                    type "lim_udp_port0";
                    must ". <= /config_data/monitoring/MonitoringWWANMainPhy/RR_MoniWWANMainPhyPortSrcTo" {
                        error-message "valmsg_it_MoniWWANMainPhyPortSrcFrom";
                    }
                    description "Monitoring - WWANMain - filter: source port (from)";
                }
                leaf "RR_MoniWWANMainPhyPortSrcTo" {
                    when "not ((/config_data/monitoring/MonitoringWWANMainPhy/RR_MoniWWANMainPhyPackType_All != 'On') and (/config_data/monitoring/MonitoringWWANMainPhy/RR_MoniWWANMainPhyPackType_Udp != 'On') and (/config_data/monitoring/MonitoringWWANMainPhy/RR_MoniWWANMainPhyPackType_Tcp != 'On'))";
                    type "lim_udp_port0";
                    must ". >= /config_data/monitoring/MonitoringWWANMainPhy/RR_MoniWWANMainPhyPortSrcFrom" {
                        error-message "valmsg_it_MoniWWANMainPhyPortSrcTo";
                    }
                    description "Monitoring - WWANMain - filter: source port (to)";
                }
                leaf "RR_MoniWWANMainPhyPortDstFrom" {
                    when "not ((/config_data/monitoring/MonitoringWWANMainPhy/RR_MoniWWANMainPhyPackType_All != 'On') and (/config_data/monitoring/MonitoringWWANMainPhy/RR_MoniWWANMainPhyPackType_Udp != 'On') and (/config_data/monitoring/MonitoringWWANMainPhy/RR_MoniWWANMainPhyPackType_Tcp != 'On'))";
                    type "lim_udp_port0";
                    must ". <= /config_data/monitoring/MonitoringWWANMainPhy/RR_MoniWWANMainPhyPortDstTo" {
                        error-message "valmsg_it_MoniWWANMainPhyPortDstFrom";
                    }
                    description "Monitoring - WWANMain - filter: destination port (from)";
                }
                leaf "RR_MoniWWANMainPhyPortDstTo" {
                    when "not ((/config_data/monitoring/MonitoringWWANMainPhy/RR_MoniWWANMainPhyPackType_All != 'On') and (/config_data/monitoring/MonitoringWWANMainPhy/RR_MoniWWANMainPhyPackType_Udp != 'On') and (/config_data/monitoring/MonitoringWWANMainPhy/RR_MoniWWANMainPhyPackType_Tcp != 'On'))";
                    type "lim_udp_port0";
                    must ". >= /config_data/monitoring/MonitoringWWANMainPhy/RR_MoniWWANMainPhyPortDstFrom" {
                        error-message "valmsg_it_MoniWWANMainPhyPortDstTo";
                    }
                    description "Monitoring - WWANMain - filter: destination port (to)";
                }
            }
        }
        container "device" {
            container "DeviceHw" {
                leaf "RR_DynHw_FreqRx_Min" {
                    type "uint32";
                }
                leaf "RR_DynHw_FreqRx_Max" {
                    type "uint32";
                }
                leaf "RR_DynHw_FreqTx_Min" {
                    type "uint32";
                }
                leaf "RR_DynHw_FreqTx_Max" {
                    type "uint32";
                }
                leaf "RR_DynHw_Module_Cellular" {
                    type "lbox_off_on";
                }
                leaf "RR_DynHw_Module_Com" {
                    type "lbox_off_on";
                }
                leaf "RR_DynHw_Module_Gps" {
                    type "lbox_off_on";
                }
                leaf "RR_DynHw_NoCrypt" {
                    type "lbox_off_on";
                }
                leaf "RR_DynHw_Primary_Radio" {
                    type "lbox_off_on";
                }
                leaf "RR_DynHw_Primary_Cellular" {
                    type "lbox_off_on";
                }
                leaf "RR_DynHw_HotStandby" {
                    type "lbox_off_on";
                }
                leaf "RR_DynHw_Port_Sfp" {
                    type "lbox_off_on";
                }
                leaf "RR_DynHw_Port_Eth_Cnt" {
                    type "uint8" {
                        range "0..7";
                    }
                }
                leaf "RR_DynHw_Port_Dido_Di_Cnt" {
                    type "uint8" {
                        range "0..3";
                    }
                }
                leaf "RR_DynHw_Port_Dido_Do_Cnt" {
                    type "uint8" {
                        range "0..3";
                    }
                }
                leaf "RR_DynHw_Radio_Antenna_Dual" {
                    type "lbox_off_on";
                }
                leaf "RR_DynHw_Radio_Modulation_Over_64QAM" {
                    type "lbox_off_on";
                }
                leaf "RR_DynHw_Radio_ChSpacing_Over_50kHz" {
                    type "lbox_off_on";
                }
                leaf "RR_DynHw_Radio_Protocol_Bdp_Base" {
                    type "lbox_off_on";
                }
                leaf "RR_DynHw_FwDistribution" {
                    type "lbox_off_on";
                }
                leaf "RR_DynHw_Port_Com1" {
                    type "lbox_off_on";
                }
                leaf "RR_DynHw_Port_Com2" {
                    type "lbox_off_on";
                }
                leaf "RR_DynHw_Port_Com3" {
                    type "lbox_off_on";
                }
                leaf "RR_DynHw_Module_Board_Com" {
                    type "lbox_off_on";
                }
                leaf "RR_DynHw_Serial_Unit" {
                    type "string";
                }
                leaf "RR_DynHw_Serial_Modem" {
                    type "string";
                }
                leaf "RR_DynHw_Serial_Radio" {
                    type "string";
                }
                leaf "RR_DynHw_Mac_Radio" {
                    type "yang:mac-address";
                }
                leaf "RR_DynHw_Mac_Eth1" {
                    type "yang:mac-address";
                }
                leaf "RR_DynHw_Mac_Eth2" {
                    type "yang:mac-address";
                }
                leaf "RR_DynHw_Mac_Eth3" {
                    type "yang:mac-address";
                }
                leaf "RR_DynHw_Mac_Eth4" {
                    type "yang:mac-address";
                }
                leaf "RR_DynHw_Mac_EthSfp1" {
                    type "yang:mac-address";
                }
                leaf "RR_DynHw_InpVoltage_Min" {
                    type "uint16";
                }
                leaf "RR_DynHw_InpVoltage_Max" {
                    type "uint16";
                }
                leaf "RR_DynHw_InpVoltage_LowDef" {
                    type "uint16";
                }
                leaf "RR_DynHw_InpVoltage_HighDef" {
                    type "uint16";
                }
                leaf "RR_DynHw_Sig_RtsCts_Com1" {
                    type "lbox_off_on";
                }
                leaf "RR_DynHw_Sig_RtsCts_Com2" {
                    type "lbox_off_on";
                }
                leaf "RR_DynHw_Sig_RtsCts_Com3" {
                    type "lbox_off_on";
                }
                leaf "RR_DynHw_Sig_DtrDsr_Com1" {
                    type "lbox_off_on";
                }
                leaf "RR_DynHw_Sig_DtrDsr_Com2" {
                    type "lbox_off_on";
                }
                leaf "RR_DynHw_Sig_DtrDsr_Com3" {
                    type "lbox_off_on";
                }
                leaf "RR_DynHw_Sig_Cd_Com1" {
                    type "lbox_off_on";
                }
                leaf "RR_DynHw_Sig_Cd_Com2" {
                    type "lbox_off_on";
                }
                leaf "RR_DynHw_Sig_Cd_Com3" {
                    type "lbox_off_on";
                }
                leaf "RR_DynHw_Sig_Ri_Com1" {
                    type "lbox_off_on";
                }
                leaf "RR_DynHw_Sig_Ri_Com2" {
                    type "lbox_off_on";
                }
                leaf "RR_DynHw_Sig_Ri_Com3" {
                    type "lbox_off_on";
                }
                leaf "RR_DynHw_Cell_Main_SvcConv" {
                    type "lbox_off_on";
                }
                leaf "RR_DynHw_Cell_Ext_SvcConv" {
                    type "lbox_off_on";
                }
                leaf "RR_DynHw_Cell_Main_SvcLpwan" {
                    type "lbox_off_on";
                }
                leaf "RR_DynHw_Cell_Ext_SvcLpwan" {
                    type "lbox_off_on";
                }
                leaf "RR_DynHw_Cell_Main_MtuMin" {
                    type "uint16" {
                        range "70..1500";
                    }
                }
                leaf "RR_DynHw_Cell_Ext_MtuMin" {
                    type "uint16" {
                        range "70..1500";
                    }
                }
                leaf "RR_DynHw_Cell_Main_Sms" {
                    type "lbox_off_on";
                }
                leaf "RR_DynHw_Cell_Ext_Sms" {
                    type "lbox_off_on";
                }
                leaf "RR_DynHw_Tamper" {
                    type "lbox_off_on";
                }
                leaf "RR_DynHw_Wifi_Ext_80211a" {
                    type "lbox_off_on";
                }
                leaf "RR_DynHw_Wifi_Ext_80211b" {
                    type "lbox_off_on";
                }
                leaf "RR_DynHw_Wifi_Ext_80211g" {
                    type "lbox_off_on";
                }
                leaf "RR_DynHw_Wifi_Ext_80211n" {
                    type "lbox_off_on";
                }
                leaf "RR_DynHw_Wifi_Ext_80211ac" {
                    type "lbox_off_on";
                }
                leaf "RR_DynHw_Wifi_Ext_TxPowerMax" {
                    type "uint8" {
                        range "1..63";
                    }
                }
                leaf "RR_DynHw_Mac_Module" {
                    type "yang:mac-address";
                }
                leaf "RR_DynHw_Module_Wifi" {
                    type "lbox_off_on";
                }
                leaf "RR_DynHw_Cell_Main_PrefSvcCatMFirst" {
                    type "lbox_off_on";
                }
                leaf "RR_DynHw_Cell_Ext_PrefSvcCatMFirst" {
                    type "lbox_off_on";
                }
                leaf "RR_DynHw_Cell_Main_PrefSvcCatMOnly" {
                    type "lbox_off_on";
                }
                leaf "RR_DynHw_Cell_Ext_PrefSvcCatMOnly" {
                    type "lbox_off_on";
                }
                leaf "RR_DynHw_Cell_Main_PrefSvcCatNbFirst" {
                    type "lbox_off_on";
                }
                leaf "RR_DynHw_Cell_Ext_PrefSvcCatNbFirst" {
                    type "lbox_off_on";
                }
                leaf "RR_DynHw_Cell_Main_PrefSvcCatNbOnly" {
                    type "lbox_off_on";
                }
                leaf "RR_DynHw_Cell_Ext_PrefSvcCatNbOnly" {
                    type "lbox_off_on";
                }
                leaf "RR_DynHw_Radio_Acm" {
                    type "lbox_off_on";
                }
                leaf "RR_DynHw_Rtc" {
                    type "lbox_off_on";
                }
                leaf "RR_DynHw_Port_Com1_Rs485" {
                    type "lbox_off_on";
                }
                leaf "RR_DynHw_Port_Com2_Rs485" {
                    type "lbox_off_on";
                }
                leaf "RR_DynHw_Port_Com3_Rs485" {
                    type "lbox_off_on";
                }
                leaf "RR_DynHw_Port_Eth_1000Mbps_Full" {
                    type "lbox_off_on";
                }
                leaf "RR_DynHw_Port_Eth_1000Mbps_Half" {
                    type "lbox_off_on";
                }
                leaf "RR_DynHw_Port_Eth_Speed" {
                    type "uint16" {
                        range "10..1000";
                    }
                }
                leaf "RR_DynHw_Radio_Freq_ChanL_Min" {
                    type "uint32";
                }
                leaf "RR_DynHw_Radio_Freq_ChanL_Max" {
                    type "uint32";
                }
                leaf "RR_DynHw_Radio_Freq_ChanH_Min" {
                    type "uint32";
                }
                leaf "RR_DynHw_Radio_Freq_ChanH_Max" {
                    type "uint32";
                }
                leaf "RR_DynHw_Radio_RfPower_Min" {
                    type "uint8";
                }
                leaf "RR_DynHw_Radio_RfPower_Max" {
                    type "uint8";
                }
                leaf "RR_DynHw_Radio_RfPower_ChanL_Min" {
                    type "uint8";
                }
                leaf "RR_DynHw_Radio_RfPower_ChanL_Max" {
                    type "uint8";
                }
                leaf "RR_DynHw_Radio_RfPower_ChanH_Min" {
                    type "uint8";
                }
                leaf "RR_DynHw_Radio_RfPower_ChanH_Max" {
                    type "uint8";
                }
                leaf "RR_DynHw_Radio_Channel_Modulation_Constraint" {
                    type "enumeration" {
                        enum "RipEX2" {
                            value "0";
                        }
                        enum "WaSP" {
                            value "1";
                        }
                    }
                }
                leaf "RR_DynHw_Radio_Duplex_Separate_Channels" {
                    type "lbox_off_on";
                }
                leaf "RR_DynHw_Radio_ModType_FSK" {
                    type "lbox_off_on";
                }
                leaf "RR_DynHw_Radio_ModType_QAM" {
                    type "lbox_off_on";
                }
                leaf "RR_DynHw_Radio_Resilience_Auto" {
                    type "lbox_off_on";
                }
                leaf "RR_DynHw_Radio_AntennaDet" {
                    type "lbox_off_on";
                }
                leaf "RR_DynHw_Radio_Protocol_Bdp" {
                    type "lbox_off_on";
                }
                leaf "RR_DynHw_Radio_RxMode_Led" {
                    type "lbox_off_on";
                }
                leaf "RR_DynHw_Radio_BBP_measurement" {
                    type "lbox_off_on";
                }
                leaf "RR_DynHw_Cell_Main_PrefSvc2gFirst" {
                    type "lbox_off_on";
                }
                leaf "RR_DynHw_Cell_Ext_PrefSvc2gFirst" {
                    type "lbox_off_on";
                }
                leaf "RR_DynHw_Cell_Main_PrefSvc2gOnly" {
                    type "lbox_off_on";
                }
                leaf "RR_DynHw_Cell_Ext_PrefSvc2gOnly" {
                    type "lbox_off_on";
                }
                leaf "RR_DynHw_Cell_Main_PrefSvc3gFirst" {
                    type "lbox_off_on";
                }
                leaf "RR_DynHw_Cell_Ext_PrefSvc3gFirst" {
                    type "lbox_off_on";
                }
                leaf "RR_DynHw_Cell_Main_PrefSvc3gOnly" {
                    type "lbox_off_on";
                }
                leaf "RR_DynHw_Cell_Ext_PrefSvc3gOnly" {
                    type "lbox_off_on";
                }
                leaf "RR_DynHw_Cell_Main_PrefSvc2g3gOnly" {
                    type "lbox_off_on";
                }
                leaf "RR_DynHw_Cell_Ext_PrefSvc2g3gOnly" {
                    type "lbox_off_on";
                }
                leaf "RR_DynHw_Cell_Main_PrefSvc4gFirst" {
                    type "lbox_off_on";
                }
                leaf "RR_DynHw_Cell_Ext_PrefSvc4gFirst" {
                    type "lbox_off_on";
                }
                leaf "RR_DynHw_Cell_Main_PrefSvc4gOnly" {
                    type "lbox_off_on";
                }
                leaf "RR_DynHw_Cell_Ext_PrefSvc4gOnly" {
                    type "lbox_off_on";
                }
                leaf "RR_DynHw_Cell_Main_PrefSvc3g4gOnly" {
                    type "lbox_off_on";
                }
                leaf "RR_DynHw_Cell_Ext_PrefSvc3g4gOnly" {
                    type "lbox_off_on";
                }
                leaf "RR_DynHw_Cell_Main_PrefSvc5gOnly" {
                    type "lbox_off_on";
                }
                leaf "RR_DynHw_Cell_Ext_PrefSvc5gOnly" {
                    type "lbox_off_on";
                }
                leaf "RR_DynHw_Cell_Main_PrefSvc3g5gOnly" {
                    type "lbox_off_on";
                }
                leaf "RR_DynHw_Cell_Ext_PrefSvc3g5gOnly" {
                    type "lbox_off_on";
                }
                leaf "RR_DynHw_Cell_Main_PrefSvc4g5gOnly" {
                    type "lbox_off_on";
                }
                leaf "RR_DynHw_Cell_Ext_PrefSvc4g5gOnly" {
                    type "lbox_off_on";
                }
                leaf "RR_DynHw_Cell_Main_PrefSvc3g4g5gOnly" {
                    type "lbox_off_on";
                }
                leaf "RR_DynHw_Cell_Ext_PrefSvc3g4g5gOnly" {
                    type "lbox_off_on";
                }
            }
            container "DeviceSwKey" {
                leaf "RR_SwKey_Flag_radio_protocols" {
                    type "lbox_off_on";
                }
                leaf "RR_SwKey_Flag_routing_bgp" {
                    type "lbox_off_on";
                }
                leaf "RR_SwKey_Flag_routing_ospf" {
                    type "lbox_off_on";
                }
                leaf "RR_SwKey_Flag_radio_modulation_over_64QAM" {
                    type "lbox_off_on";
                }
                leaf "RR_SwKey_Flag_radio_chspacing_over_50kHz" {
                    type "lbox_off_on";
                }
                leaf "RR_SwKey_Flag_radio_full_duplex" {
                    type "lbox_off_on";
                }
                leaf "RR_SwKey_Flag_radio_rfpower_over_37dBm" {
                    type "lbox_off_on";
                }
                leaf "RR_SwKey_Flag_vpn_ipsec" {
                    type "lbox_off_on";
                }
                leaf "RR_SwKey_Flag_vpn_gre" {
                    type "lbox_off_on";
                }
                leaf "RR_SwKey_Flag_adm_multiuser" {
                    type "lbox_off_on";
                }
                leaf "RR_SwKey_Flag_adm_radius" {
                    type "lbox_off_on";
                }
                leaf "RR_SwKey_Flag_interface_sfp" {
                    type "lbox_off_on";
                }
                leaf "RR_SwKey_Flag_routing_babel" {
                    type "lbox_off_on";
                }
                leaf "RR_SwKey_Flag_interface_db9_com2" {
                    type "lbox_off_on";
                }
                leaf "RR_SwKey_Flag_routing_link_management" {
                    type "lbox_off_on";
                }
                leaf "RR_SwKey_Flag_vpn_openvpn" {
                    type "lbox_off_on";
                }
                leaf "RR_SwKey_Flag_interface_pppoe_client" {
                    type "lbox_off_on";
                }
                leaf "RR_SwKey_Flag_radio_acm" {
                    type "lbox_off_on";
                }
                leaf "RR_SwKey_Flag_mqtt" {
                    type "lbox_off_on";
                }
            }
        }
        container "region" {
            container "Region" {
                leaf "RR_DynReg_FreqInterval_0_Min" {
                    type "uint32";
                }
                leaf "RR_DynReg_FreqInterval_0_Max" {
                    type "uint32";
                }
                leaf "RR_DynReg_FreqInterval_1_Min" {
                    type "uint32";
                }
                leaf "RR_DynReg_FreqInterval_1_Max" {
                    type "uint32";
                }
                leaf "RR_DynReg_FreqInterval_2_Min" {
                    type "uint32";
                }
                leaf "RR_DynReg_FreqInterval_2_Max" {
                    type "uint32";
                }
                leaf "RR_DynReg_FreqInterval_3_Min" {
                    type "uint32";
                }
                leaf "RR_DynReg_FreqInterval_3_Max" {
                    type "uint32";
                }
                leaf "RR_DynReg_FreqInterval_4_Min" {
                    type "uint32";
                }
                leaf "RR_DynReg_FreqInterval_4_Max" {
                    type "uint32";
                }
                leaf "RR_DynReg_FreqInterval_5_Min" {
                    type "uint32";
                }
                leaf "RR_DynReg_FreqInterval_5_Max" {
                    type "uint32";
                }
                leaf "RR_DynReg_FreqInterval_6_Min" {
                    type "uint32";
                }
                leaf "RR_DynReg_FreqInterval_6_Max" {
                    type "uint32";
                }
                leaf "RR_DynReg_FreqInterval_7_Min" {
                    type "uint32";
                }
                leaf "RR_DynReg_FreqInterval_7_Max" {
                    type "uint32";
                }
                leaf "RR_DynReg_RfPower_Val_20_En" {
                    type "lbox_off_on";
                }
                leaf "RR_DynReg_RfPower_Val_21_En" {
                    type "lbox_off_on";
                }
                leaf "RR_DynReg_RfPower_Val_22_En" {
                    type "lbox_off_on";
                }
                leaf "RR_DynReg_RfPower_Val_23_En" {
                    type "lbox_off_on";
                }
                leaf "RR_DynReg_RfPower_Val_24_En" {
                    type "lbox_off_on";
                }
                leaf "RR_DynReg_RfPower_Val_25_En" {
                    type "lbox_off_on";
                }
                leaf "RR_DynReg_RfPower_Val_26_En" {
                    type "lbox_off_on";
                }
                leaf "RR_DynReg_RfPower_Val_27_En" {
                    type "lbox_off_on";
                }
                leaf "RR_DynReg_RfPower_Val_28_En" {
                    type "lbox_off_on";
                }
                leaf "RR_DynReg_RfPower_Val_29_En" {
                    type "lbox_off_on";
                }
                leaf "RR_DynReg_RfPower_Val_30_En" {
                    type "lbox_off_on";
                }
                leaf "RR_DynReg_RfPower_Val_31_En" {
                    type "lbox_off_on";
                }
                leaf "RR_DynReg_RfPower_Val_32_En" {
                    type "lbox_off_on";
                }
                leaf "RR_DynReg_RfPower_Val_33_En" {
                    type "lbox_off_on";
                }
                leaf "RR_DynReg_RfPower_Val_34_En" {
                    type "lbox_off_on";
                }
                leaf "RR_DynReg_RfPower_Val_35_En" {
                    type "lbox_off_on";
                }
                leaf "RR_DynReg_RfPower_Val_36_En" {
                    type "lbox_off_on";
                }
                leaf "RR_DynReg_RfPower_Val_37_En" {
                    type "lbox_off_on";
                }
                leaf "RR_DynReg_RfPower_Val_38_En" {
                    type "lbox_off_on";
                }
                leaf "RR_DynReg_RfPower_Val_39_En" {
                    type "lbox_off_on";
                }
                leaf "RR_DynReg_RfPower_Val_40_En" {
                    type "lbox_off_on";
                }
                leaf "RR_DynReg_ChSpacing_Val_0_En" {
                    type "lbox_off_on";
                }
                leaf "RR_DynReg_ChSpacing_Val_1_En" {
                    type "lbox_off_on";
                }
                leaf "RR_DynReg_ChSpacing_Val_2_En" {
                    type "lbox_off_on";
                }
                leaf "RR_DynReg_ChSpacing_Val_3_En" {
                    type "lbox_off_on";
                }
                leaf "RR_DynReg_ChSpacing_Val_4_En" {
                    type "lbox_off_on";
                }
                leaf "RR_DynReg_ChSpacing_Val_5_En" {
                    type "lbox_off_on";
                }
                leaf "RR_DynReg_ChSpacing_Val_6_En" {
                    type "lbox_off_on";
                }
                leaf "RR_DynReg_ChSpacing_Val_7_En" {
                    type "lbox_off_on";
                }
                leaf "RR_DynReg_ChSpacing_Val_8_En" {
                    type "lbox_off_on";
                }
                leaf "RR_DynReg_ChSpacing_Val_9_En" {
                    type "lbox_off_on";
                }
                leaf "RR_DynReg_ChSpacing_Val_10_En" {
                    type "lbox_off_on";
                }
                leaf "RR_DynReg_ChSpacing_Val_11_En" {
                    type "lbox_off_on";
                }
                leaf "RR_DynReg_ChSpacing_Val_12_En" {
                    type "lbox_off_on";
                }
                leaf "RR_DynReg_ChSpacing_Val_13_En" {
                    type "lbox_off_on";
                }
                leaf "RR_DynReg_ChSpacing_Val_14_En" {
                    type "lbox_off_on";
                }
                leaf "RR_DynReg_ChSpacing_Val_15_En" {
                    type "lbox_off_on";
                }
                leaf "RR_DynReg_ChOccupied_Val_0_En" {
                    type "lbox_off_on";
                }
                leaf "RR_DynReg_ChOccupied_Val_1_En" {
                    type "lbox_off_on";
                }
                leaf "RR_DynReg_ChOccupied_Val_2_En" {
                    type "lbox_off_on";
                }
                leaf "RR_DynReg_ChOccupied_Val_3_En" {
                    type "lbox_off_on";
                }
                leaf "RR_DynReg_ChOccupied_Val_4_En" {
                    type "lbox_off_on";
                }
                leaf "RR_DynReg_ChOccupied_Val_5_En" {
                    type "lbox_off_on";
                }
                leaf "RR_DynReg_ChOccupied_Val_6_En" {
                    type "lbox_off_on";
                }
                leaf "RR_DynReg_ChOccupied_Val_7_En" {
                    type "lbox_off_on";
                }
                leaf "RR_DynReg_ChOccupied_Val_8_En" {
                    type "lbox_off_on";
                }
                leaf "RR_DynReg_ChOccupied_Val_9_En" {
                    type "lbox_off_on";
                }
                leaf "RR_DynReg_ChOccupied_Val_10_En" {
                    type "lbox_off_on";
                }
                leaf "RR_DynReg_ChOccupied_Val_11_En" {
                    type "lbox_off_on";
                }
                leaf "RR_DynReg_ChOccupied_Val_12_En" {
                    type "lbox_off_on";
                }
                leaf "RR_DynReg_ChOccupied_Val_13_En" {
                    type "lbox_off_on";
                }
                leaf "RR_DynReg_ChOccupied_Val_14_En" {
                    type "lbox_off_on";
                }
                leaf "RR_DynReg_ChOccupied_Val_15_En" {
                    type "lbox_off_on";
                }
                leaf "RR_DynReg_ChOccupied_Val_16_En" {
                    type "lbox_off_on";
                }
                leaf "RR_DynReg_ChOccupied_Val_17_En" {
                    type "lbox_off_on";
                }
                leaf "RR_DynReg_ChOccupied_Val_18_En" {
                    type "lbox_off_on";
                }
                leaf "RR_DynReg_ChOccupied_Val_19_En" {
                    type "lbox_off_on";
                }
                leaf "RR_DynReg_ChOccupied_Val_20_En" {
                    type "lbox_off_on";
                }
                leaf "RR_DynReg_ChOccupied_Val_21_En" {
                    type "lbox_off_on";
                }
                leaf "RR_DynReg_ChOccupied_Val_22_En" {
                    type "lbox_off_on";
                }
                leaf "RR_DynReg_ChOccupied_Val_23_En" {
                    type "lbox_off_on";
                }
                leaf "RR_DynReg_ChOccupied_Val_24_En" {
                    type "lbox_off_on";
                }
                leaf "RR_DynReg_Frequency_Fallback" {
                    type "uint32";
                }
                leaf "RR_DynReg_RfPower_Fallback" {
                    type "uint8";
                }
                leaf "RR_DynReg_ChSpacing_Fallback" {
                    type "uint16";
                }
                leaf "RR_DynReg_ChOccupied_Fallback" {
                    type "uint16";
                }
            }
            list "RR_S_TABLE_RegionFreqIntervals" {
                key "ID";
                description "Cnf. group for dynamic configuration: row of table RegionFreqIntervals";
                leaf "ID" {
                    type "lim_uint_16";
                }
                leaf "DynReg_FreqIval_Min" {
                    type "uint32";
                    default "0";
                }
                leaf "DynReg_FreqIval_Max" {
                    type "uint32";
                    default "0";
                }
            }
            list "RR_S_TABLE_RegionRfPowerVals" {
                key "ID";
                description "Cnf. group for dynamic configuration: row of table RegionRfPowerVals";
                leaf "ID" {
                    type "lim_uint_16";
                }
                leaf "DynReg_RfPwrVal_Val" {
                    type "uint8";
                    default "0";
                }
            }
            list "RR_S_TABLE_RegionChSpacingVals" {
                key "ID";
                description "Cnf. group for dynamic configuration: row of table RegionChSpacingVals";
                leaf "ID" {
                    type "lim_uint_16";
                }
                leaf "DynReg_ChSpcVal_Val" {
                    type "uint16";
                    default "0";
                }
            }
            list "RR_S_TABLE_RegionChOccupiedVals" {
                key "ID";
                description "Cnf. group for dynamic configuration: row of table RegionChOccupiedVals";
                leaf "ID" {
                    type "lim_uint_16";
                }
                leaf "DynReg_ChOccVal_Val" {
                    type "uint16";
                    default "0";
                }
            }
        }
        container "com_1_prot" {
            when "not ((/config_data/device/DeviceHw/RR_DynHw_Port_Com1 != 'On') or (/config_data/main/ComPort_1/RR_ComPort_1_ENA != 'On'))";
            presence "Port / Terminal server enabled.";
            leaf "_variant_source_ref" {
                type "instance-identifier";
                default "/rr:config_data/rr:main/rr:ComPort_1/rr:RR_ComPort_1_Protocol";
            }
            uses "SerialProtocol";
        }
        container "com_2_prot" {
            when "not ((/config_data/device/DeviceHw/RR_DynHw_Port_Com2 != 'On') or (/config_data/main/ComPort_2/RR_ComPort_2_ENA != 'On'))";
            presence "Port / Terminal server enabled.";
            leaf "_variant_source_ref" {
                type "instance-identifier";
                default "/rr:config_data/rr:main/rr:ComPort_2/rr:RR_ComPort_2_Protocol";
            }
            uses "SerialProtocol";
        }
        container "com_3_prot" {
            when "not ((/config_data/device/DeviceHw/RR_DynHw_Port_Com3 != 'On') or (/config_data/main/ComPort_3/RR_ComPort_3_ENA != 'On'))";
            presence "Port / Terminal server enabled.";
            leaf "_variant_source_ref" {
                type "instance-identifier";
                default "/rr:config_data/rr:main/rr:ComPort_3/rr:RR_ComPort_3_Protocol";
            }
            uses "SerialProtocol";
        }
        container "term_server_1_prot" {
            when "not (/config_data/main/TerminalServer_1/RR_TerminalServer_1_ENA != 'On')";
            presence "Port / Terminal server enabled.";
            leaf "_variant_source_ref" {
                type "instance-identifier";
                default "/rr:config_data/rr:main/rr:TerminalServer_1/rr:RR_TerminalServer_1_Protocol";
            }
            uses "TermServerProtocol";
        }
        container "term_server_2_prot" {
            when "not (/config_data/main/TerminalServer_2/RR_TerminalServer_2_ENA != 'On')";
            presence "Port / Terminal server enabled.";
            leaf "_variant_source_ref" {
                type "instance-identifier";
                default "/rr:config_data/rr:main/rr:TerminalServer_2/rr:RR_TerminalServer_2_Protocol";
            }
            uses "TermServerProtocol";
        }
        container "term_server_3_prot" {
            when "not (/config_data/main/TerminalServer_3/RR_TerminalServer_3_ENA != 'On')";
            presence "Port / Terminal server enabled.";
            leaf "_variant_source_ref" {
                type "instance-identifier";
                default "/rr:config_data/rr:main/rr:TerminalServer_3/rr:RR_TerminalServer_3_Protocol";
            }
            uses "TermServerProtocol";
        }
        container "term_server_4_prot" {
            when "not (/config_data/main/TerminalServer_4/RR_TerminalServer_4_ENA != 'On')";
            presence "Port / Terminal server enabled.";
            leaf "_variant_source_ref" {
                type "instance-identifier";
                default "/rr:config_data/rr:main/rr:TerminalServer_4/rr:RR_TerminalServer_4_Protocol";
            }
            uses "TermServerProtocol";
        }
        container "term_server_5_prot" {
            when "not (/config_data/main/TerminalServer_5/RR_TerminalServer_5_ENA != 'On')";
            presence "Port / Terminal server enabled.";
            leaf "_variant_source_ref" {
                type "instance-identifier";
                default "/rr:config_data/rr:main/rr:TerminalServer_5/rr:RR_TerminalServer_5_Protocol";
            }
            uses "TermServerProtocol";
        }
    }
    container "Diagnostics" {
        grouping "Error_message" {
            container "message_params" {
                description "Optional error message parameters.";
            }
            leaf "message_id" {
                type "string";
                mandatory "true";
            }
        }
        grouping "Error" {
            container "error" {
                presence "An error occured during processing rpc request.
        Container \"result\" may or may not be present simultaneously.";
                description "General RPC error message definition";
                leaf "code" {
                    type "enumeration" {
                        enum "rpc_server_error";
                        enum "rpc_compatibility_error";
                        enum "rpc_invalid_request";
                        enum "rpc_temporarily_unavailable";
                        enum "rpc_method_not_found";
                        enum "rpc_permission_denied";
                        enum "rpc_async_action_in_progress";
                    }
                    mandatory "true";
                }
                leaf "log" {
                    type "string";
                }
                list "suberrors" {
                    leaf-list "seids" {
                        type "string";
                    }
                    uses "Error_message";
                }
                uses "Error_message";
            }
        }
        grouping "Version_and_id" {
            leaf "id" {
                type "string";
            }
            leaf "version" {
                type "string";
            }
        }
        grouping "Input_header" {
            leaf "target" {
                type "inet:ipv4-address";
                mandatory "true";
            }
            uses "Version_and_id";
        }
        action "statistics_data_get" {
            input {
                container "params" {
                    container "filter" {
                        leaf "tstamp_from" {
                            type "uint64";
                            mandatory "true";
                        }
                        leaf "tstamp_until" {
                            type "uint64";
                            must ". > ../tstamp_from" {
                                error-message "valmsg_tstamp_until_before_from";
                            }
                        }
                        leaf-list "types" {
                            type "enumeration" {
                                enum "stat_rlp_ifc";
                                enum "stat_rlp_proto";
                                enum "stat_rlp_proto_na";
                                enum "stat_rlp_sig";
                                enum "stat_rlp_sig_na";
                                enum "stat_sp";
                                enum "stat_eth";
                                enum "stat_cell_data";
                                enum "stat_cell_state";
                                enum "stat_cell_sig";
                                enum "stat_wifi_data";
                                enum "stat_wifi_sta_data";
                                enum "stat_wifi_sta_sig";
                                enum "stat_meas_data";
                            }
                            min-elements "1";
                            ordered-by "user";
                        }
                    }
                }
                uses "Input_header";
            }
            output {
                container "result" {
                    typedef "stat_counter_t" {
                        type "uint64";
                    }
                    typedef "stat_percent_t" {
                        type "uint32" {
                            range "0..100";
                        }
                    }
                    typedef "stat_int1000_t" {
                        type "int32" {
                            range "-1000..1000";
                        }
                    }
                    grouping "avg_min_max" {
                        leaf "avg" {
                            type "stat_int1000_t";
                        }
                        leaf "min" {
                            type "stat_int1000_t";
                        }
                        leaf "max" {
                            type "stat_int1000_t";
                        }
                    }
                    grouping "avg_min_max_dev" {
                        leaf "dev" {
                            type "stat_int1000_t";
                        }
                        uses "avg_min_max";
                    }
                    grouping "rx_tx_count_bytes" {
                        leaf "rx_count" {
                            type "stat_counter_t";
                        }
                        leaf "rx_bytes" {
                            type "stat_counter_t";
                        }
                        leaf "tx_count" {
                            type "stat_counter_t";
                        }
                        leaf "tx_bytes" {
                            type "stat_counter_t";
                        }
                    }
                    grouping "IP_proto" {
                        container "UDP" {
                            uses "rx_tx_count_bytes";
                        }
                        container "TCP" {
                            uses "rx_tx_count_bytes";
                        }
                        container "ICMP" {
                            uses "rx_tx_count_bytes";
                        }
                        container "ARP" {
                            uses "rx_tx_count_bytes";
                        }
                        container "Other" {
                            uses "rx_tx_count_bytes";
                        }
                    }
                    grouping "att12" {
                        container "att2" {
                            uses "avg_min_max";
                        }
                        leaf "att1" {
                            type "stat_percent_t";
                        }
                    }
                    container "stat_rlp" {
                        container "stat_rlp_proto_na" {
                            leaf "False_sync" {
                                type "stat_counter_t";
                            }
                            leaf "Subhdr_err" {
                                type "stat_counter_t";
                            }
                            leaf "Phy_err" {
                                type "stat_counter_t";
                            }
                            leaf "Hdr_err" {
                                type "stat_counter_t";
                            }
                            leaf "Incompatible" {
                                type "stat_counter_t";
                            }
                            leaf "Strange" {
                                type "stat_counter_t";
                            }
                            leaf "Unroutable" {
                                type "stat_counter_t";
                            }
                            leaf "nullptr" {
                                type "stat_counter_t";
                            }
                        }
                        container "stat_rlp_sig_na" {
                            container "Preframe_noise" {
                                container "rss" {
                                    uses "avg_min_max_dev";
                                }
                                container "att" {
                                    uses "att12";
                                }
                                leaf "count" {
                                    type "stat_counter_t";
                                }
                            }
                            container "Hdrerr_other" {
                                container "rss" {
                                    uses "avg_min_max_dev";
                                }
                                container "mse" {
                                    uses "avg_min_max_dev";
                                }
                                leaf "count" {
                                    type "stat_counter_t";
                                }
                            }
                            leaf "nullptr" {
                                type "stat_counter_t";
                            }
                        }
                        list "stat_rlp_ifc" {
                            key "Link_address";
                            leaf "Link_address" {
                                type "string";
                            }
                            leaf "IP_address" {
                                type "inet:ipv4-address";
                            }
                            leaf "nullptr" {
                                type "stat_counter_t";
                            }
                            uses "IP_proto";
                        }
                        list "stat_rlp_proto" {
                            key "Link_address";
                            container "Frame" {
                                leaf "rx_ok" {
                                    type "stat_counter_t";
                                }
                                leaf "rx_error" {
                                    type "stat_counter_t";
                                }
                                leaf "rx_dupl" {
                                    type "stat_counter_t";
                                }
                                leaf "tx_ok" {
                                    type "stat_counter_t";
                                }
                                leaf "tx_lost" {
                                    type "stat_counter_t";
                                }
                                leaf "tx_rep" {
                                    type "stat_counter_t";
                                }
                                leaf "tx_rej" {
                                    type "stat_counter_t";
                                }
                            }
                            container "Packet" {
                                leaf "rx_rej" {
                                    type "stat_counter_t";
                                }
                                leaf "tx_rej" {
                                    type "stat_counter_t";
                                }
                            }
                            container "Ctrl" {
                                leaf "rx_frame" {
                                    type "stat_counter_t";
                                }
                                leaf "tx_frame" {
                                    type "stat_counter_t";
                                }
                            }
                            container "Total" {
                                uses "rx_tx_count_bytes";
                            }
                            leaf "Link_address" {
                                type "string";
                            }
                            leaf "IP_address" {
                                type "inet:ipv4-address";
                            }
                            leaf "nullptr" {
                                type "stat_counter_t";
                            }
                        }
                        list "stat_rlp_sig" {
                            key "Link_address";
                            container "Rss" {
                                uses "avg_min_max_dev";
                            }
                            container "Subhdr_mse" {
                                uses "avg_min_max_dev";
                            }
                            container "Att" {
                                uses "att12";
                            }
                            container "Data" {
                                container "mse" {
                                    uses "avg_min_max_dev";
                                }
                                leaf "count" {
                                    type "stat_counter_t";
                                }
                            }
                            leaf "Link_address" {
                                type "string";
                            }
                            leaf "IP_address" {
                                type "inet:ipv4-address";
                            }
                            leaf "Frame_count" {
                                type "stat_counter_t";
                            }
                            leaf "Freq_offset" {
                                type "int32";
                            }
                            leaf "nullptr" {
                                type "stat_counter_t";
                            }
                        }
                    }
                    container "stat_wifi_data" {
                        container "UDP" {
                            uses "rx_tx_count_bytes";
                        }
                        container "TCP" {
                            uses "rx_tx_count_bytes";
                        }
                        container "ICMP" {
                            uses "rx_tx_count_bytes";
                        }
                        container "IPv4_other" {
                            uses "rx_tx_count_bytes";
                        }
                        container "Sms" {
                            leaf "rx_ok" {
                                type "stat_counter_t";
                            }
                            leaf "rx_rej" {
                                type "stat_counter_t";
                            }
                            leaf "tx_ok" {
                                type "stat_counter_t";
                            }
                        }
                        leaf "Interface" {
                            type "stat_counter_t";
                        }
                        leaf "nullptr" {
                            type "stat_counter_t";
                        }
                    }
                    container "stat_wifi_sta_data" {
                        container "Packet" {
                            leaf "rx_drop" {
                                type "stat_counter_t";
                            }
                            leaf "rx_err" {
                                type "stat_counter_t";
                            }
                            leaf "tx_ret" {
                                type "stat_counter_t";
                            }
                            leaf "tx_fail" {
                                type "stat_counter_t";
                            }
                        }
                        container "Total" {
                            uses "rx_tx_count_bytes";
                        }
                        leaf "Interface" {
                            type "stat_counter_t";
                        }
                        leaf "MAC_address" {
                            type "stat_counter_t";
                        }
                        leaf "nullptr" {
                            type "stat_counter_t";
                        }
                    }
                    container "stat_wifi_sta_sig" {
                        container "Overall" {
                            container "rss" {
                                uses "avg_min_max_dev";
                            }
                            leaf "samples" {
                                type "stat_counter_t";
                            }
                        }
                        container "Ant1" {
                            container "rss" {
                                uses "avg_min_max_dev";
                            }
                            leaf "samples" {
                                type "stat_counter_t";
                            }
                        }
                        container "Ant2" {
                            container "rss" {
                                uses "avg_min_max_dev";
                            }
                            leaf "samples" {
                                type "stat_counter_t";
                            }
                        }
                        leaf "Interface" {
                            type "stat_counter_t";
                        }
                        leaf "MAC_address" {
                            type "stat_counter_t";
                        }
                        leaf "nullptr" {
                            type "stat_counter_t";
                        }
                    }
                    list "stat_cell" {
                        key "Interface";
                        container "stat_cell_data" {
                            container "UDP" {
                                uses "rx_tx_count_bytes";
                            }
                            container "TCP" {
                                uses "rx_tx_count_bytes";
                            }
                            container "ICMP" {
                                uses "rx_tx_count_bytes";
                            }
                            container "IPv4_other" {
                                uses "rx_tx_count_bytes";
                            }
                            container "Sms" {
                                leaf "rx_ok" {
                                    type "stat_counter_t";
                                }
                                leaf "rx_rej" {
                                    type "stat_counter_t";
                                }
                                leaf "tx_ok" {
                                    type "stat_counter_t";
                                }
                            }
                            leaf "nullptr" {
                                type "stat_counter_t";
                            }
                        }
                        container "stat_cell_state" {
                            container "Sim" {
                                leaf "SIM1" {
                                    type "stat_percent_t";
                                }
                                leaf "SIM2" {
                                    type "stat_percent_t";
                                }
                            }
                            container "Service" {
                                container "Cat" {
                                    leaf "M" {
                                        type "stat_counter_t";
                                    }
                                    leaf "NB" {
                                        type "stat_counter_t";
                                    }
                                }
                                leaf "NA" {
                                    type "stat_percent_t";
                                }
                                leaf "_2G" {
                                    type "stat_percent_t";
                                }
                                leaf "_3G" {
                                    type "stat_percent_t";
                                }
                                leaf "_4G" {
                                    type "stat_percent_t";
                                }
                                leaf "_5G" {
                                    type "stat_percent_t";
                                }
                            }
                            container "Network" {
                                leaf "NC" {
                                    type "stat_percent_t";
                                }
                                leaf "home" {
                                    type "stat_percent_t";
                                }
                                leaf "roam" {
                                    type "stat_percent_t";
                                }
                                leaf "other" {
                                    type "stat_percent_t";
                                }
                            }
                            leaf "nullptr" {
                                type "stat_counter_t";
                            }
                        }
                        container "stat_cell_sig" {
                            container "_2G" {
                                container "rssi" {
                                    uses "avg_min_max_dev";
                                }
                                leaf "count" {
                                    type "stat_counter_t";
                                }
                            }
                            container "_3G" {
                                container "rscp" {
                                    uses "avg_min_max_dev";
                                }
                                leaf "count" {
                                    type "stat_counter_t";
                                }
                            }
                            container "_4G" {
                                container "rsrp" {
                                    uses "avg_min_max_dev";
                                }
                                leaf "count" {
                                    type "stat_counter_t";
                                }
                            }
                            container "_5G" {
                                container "ss_rsrp" {
                                    uses "avg_min_max_dev";
                                }
                                leaf "count" {
                                    type "stat_counter_t";
                                }
                            }
                            container "cat" {
                                container "m" {
                                    container "rsrp" {
                                        uses "avg_min_max_dev";
                                    }
                                    leaf "count" {
                                        type "stat_counter_t";
                                    }
                                }
                                container "nb" {
                                    container "rsrp" {
                                        uses "avg_min_max_dev";
                                    }
                                    leaf "count" {
                                        type "stat_counter_t";
                                    }
                                }
                            }
                            leaf "nullptr" {
                                type "stat_counter_t";
                            }
                        }
                        leaf "Interface" {
                            type "enumeration" {
                                enum "cell-ext";
                                enum "cell-main";
                            }
                        }
                    }
                    list "stat_sp" {
                        key "Interface";
                        container "Correct" {
                            uses "rx_tx_count_bytes";
                        }
                        container "Drop" {
                            uses "rx_tx_count_bytes";
                        }
                        leaf "Interface" {
                            type "stat_counter_t";
                        }
                        leaf "nullptr" {
                            type "stat_counter_t";
                        }
                    }
                    list "stat_eth" {
                        key "Interface";
                        container "VLAN" {
                            uses "rx_tx_count_bytes";
                        }
                        container "Multicast" {
                            uses "rx_tx_count_bytes";
                        }
                        container "IPv4_other" {
                            uses "rx_tx_count_bytes";
                        }
                        container "IPv6" {
                            uses "rx_tx_count_bytes";
                        }
                        leaf "Interface" {
                            type "stat_counter_t";
                        }
                        leaf "nullptr" {
                            type "stat_counter_t";
                        }
                        uses "IP_proto";
                    }
                    list "stat_meas_data" {
                        key "Sensor";
                        container "Meas" {
                            leaf "count" {
                                type "stat_counter_t";
                            }
                            uses "avg_min_max";
                        }
                        leaf "Sensor" {
                            type "string";
                        }
                        leaf "nullptr" {
                            type "stat_counter_t";
                        }
                    }
                }
                uses "Version_and_id";
                uses "Error";
            }
        }
    }
}
