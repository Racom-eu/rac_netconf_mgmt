module test-module {
    yang-version 1.1;
    namespace "urn:test:module";
    prefix tm;

    revision 2024-01-01 {
        description "Test module for unit tests.";
    }

    container settings {
        leaf name {
            type string;
        }
        leaf count {
            type uint32;
        }
    }
}
